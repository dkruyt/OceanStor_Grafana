--
-- HUAWEI-STORAGE-HARDWARE-MIB.mib
-- MIB generated by MG-SOFT Visual MIB Builder Version 4.0 Build 347
-- Friday, October 17, 2014 at 18:50:14
--

	HUAWEI-STORAGE-HARDWARE-MIB DEFINITIONS ::= BEGIN
 
		IMPORTS
			OBJECT-GROUP, MODULE-COMPLIANCE			
				FROM SNMPv2-CONF			
			enterprises, Integer32, Unsigned32, Counter64, 
			OBJECT-TYPE, MODULE-IDENTITY			
				FROM SNMPv2-SMI			
			TEXTUAL-CONVENTION			
				FROM SNMPv2-TC;
	
	
		hwStorage MODULE-IDENTITY 
			LAST-UPDATED "201008111239Z"		-- August 11, 2010 at 12:39 GMT
			ORGANIZATION 
				"Huawei Technologies Co.,Ltd."
			CONTACT-INFO 
				"Huawei Industrial Base
				Bantian, Longgang
				Shenzhen 518129
				People's Republic of China
				Website: http://www.huawei.com
				Email: support@huawei.com"
			DESCRIPTION 
				"Description."
			REVISION "201404061354Z"		-- April 06, 2014 at 13:54 GMT
			DESCRIPTION 
				" "
			::= { huaweistorage 4 }

		
	
--
-- Textual conventions
--
	
--  August 11, 2010 at 12:39 GMT
-- April 06, 2014 at 13:54 GMT
-- 
-- Textual conventions
-- 
		NodeCodeString ::= TEXTUAL-CONVENTION
			DISPLAY-HINT 
				"255a"
			STATUS current
			DESCRIPTION 
				"characters in length."
			SYNTAX OCTET STRING (SIZE (15..17))

	
--
-- Node definitions
--
	
		huaweistorage OBJECT IDENTIFIER ::= { enterprises 34774 }

		
		hwISM OBJECT IDENTIFIER ::= { hwStorage 1 }

		
		hwStorageDevice OBJECT IDENTIFIER ::= { hwISM 23 }

		
		hwHardwareInfo OBJECT IDENTIFIER ::= { hwStorageDevice 5 }

		
		hwInfoDiskTable OBJECT-TYPE
			SYNTAX SEQUENCE OF HwInfoDiskEntry
			MAX-ACCESS not-accessible
			STATUS current
			DESCRIPTION
				" "
			::= { hwHardwareInfo 1 }

		
		hwInfoDiskEntry OBJECT-TYPE
			SYNTAX HwInfoDiskEntry
			MAX-ACCESS not-accessible
			STATUS current
			DESCRIPTION
				" "
			INDEX { hwInfoDiskID }
			::= { hwInfoDiskTable 1 }

		
		HwInfoDiskEntry ::=
			SEQUENCE { 
				hwInfoDiskID
					OCTET STRING,
				hwInfoDiskHealthStatus
					Unsigned32,
				hwInfoDiskRunningStatus
					Unsigned32,
				hwInfoDiskLocation
					OCTET STRING,
				hwInfoDiskType
					Unsigned32,
				hwInfoDiskCapacity
					Counter64,
				hwInfoDiskRole
					Unsigned32,
				hwInfoDiskSpeed
					Unsigned32,
				hwInfoDiskInterfaceBandwidth
					Unsigned32,
				hwInfoDiskSectorSize
					Unsigned32,
				hwInfoDiskTemperature
					Integer32,
				hwInfoDiskModel
					OCTET STRING,
				hwInfoDiskFirmwareVersion
					OCTET STRING,
				hwInfoDiskManufacturer
					OCTET STRING,
				hwInfoDiskSerialNumber
					OCTET STRING,
				hwInfoDiskLightStatus
					Unsigned32,
				hwInfoDiskDiskDomainID
					OCTET STRING,
				hwInfoDiskDiskDomainName
					OCTET STRING,
				hwInfoDiskDiskDomainTierID
					OCTET STRING,
				hwInfoDiskCofferDisk
					Unsigned32,
				hwInfoDiskRunTime
					Unsigned32,
				hwInfoDiskProgress
					Unsigned32,
				hwInfoDiskBarCode
					OCTET STRING,
				hwInfoDiskCapacityUsage
					Unsigned32,
				hwInfoDiskHealthMark
					Unsigned32
			 }

		hwInfoDiskID OBJECT-TYPE
			SYNTAX OCTET STRING
			MAX-ACCESS read-only
			STATUS current
			DESCRIPTION
				"  "
			::= { hwInfoDiskEntry 1 }

		
		hwInfoDiskHealthStatus OBJECT-TYPE
			SYNTAX Unsigned32
			MAX-ACCESS read-only
			STATUS current
			DESCRIPTION
				"  "
			::= { hwInfoDiskEntry 2 }

		
		hwInfoDiskRunningStatus OBJECT-TYPE
			SYNTAX Unsigned32
			MAX-ACCESS read-only
			STATUS current
			DESCRIPTION
				"  "
			::= { hwInfoDiskEntry 3 }

		
		hwInfoDiskLocation OBJECT-TYPE
			SYNTAX OCTET STRING
			MAX-ACCESS read-only
			STATUS current
			DESCRIPTION
				"  "
			::= { hwInfoDiskEntry 4 }

		
		hwInfoDiskType OBJECT-TYPE
			SYNTAX Unsigned32
			MAX-ACCESS read-only
			STATUS current
			DESCRIPTION
				"  "
			::= { hwInfoDiskEntry 5 }

		
		hwInfoDiskCapacity OBJECT-TYPE
			SYNTAX Counter64
			MAX-ACCESS read-only
			STATUS current
			DESCRIPTION
				"  "
			::= { hwInfoDiskEntry 6 }

		
		hwInfoDiskRole OBJECT-TYPE
			SYNTAX Unsigned32
			MAX-ACCESS read-only
			STATUS current
			DESCRIPTION
				" "
			::= { hwInfoDiskEntry 7 }

		
		hwInfoDiskSpeed OBJECT-TYPE
			SYNTAX Unsigned32
			MAX-ACCESS read-only
			STATUS current
			DESCRIPTION
				"  "
			::= { hwInfoDiskEntry 8 }

		
		hwInfoDiskInterfaceBandwidth OBJECT-TYPE
			SYNTAX Unsigned32
			MAX-ACCESS read-only
			STATUS current
			DESCRIPTION
				"  "
			::= { hwInfoDiskEntry 9 }

		
		hwInfoDiskSectorSize OBJECT-TYPE
			SYNTAX Unsigned32
			MAX-ACCESS read-only
			STATUS current
			DESCRIPTION
				"  "
			::= { hwInfoDiskEntry 10 }

		
		hwInfoDiskTemperature OBJECT-TYPE
			SYNTAX Integer32
			MAX-ACCESS read-only
			STATUS current
			DESCRIPTION
				"  "
			::= { hwInfoDiskEntry 11 }

		
		hwInfoDiskModel OBJECT-TYPE
			SYNTAX OCTET STRING
			MAX-ACCESS read-only
			STATUS current
			DESCRIPTION
				"  "
			::= { hwInfoDiskEntry 12 }

		
		hwInfoDiskFirmwareVersion OBJECT-TYPE
			SYNTAX OCTET STRING
			MAX-ACCESS read-only
			STATUS current
			DESCRIPTION
				"  "
			::= { hwInfoDiskEntry 13 }

		
		hwInfoDiskManufacturer OBJECT-TYPE
			SYNTAX OCTET STRING
			MAX-ACCESS read-only
			STATUS current
			DESCRIPTION
				"  "
			::= { hwInfoDiskEntry 14 }

		
		hwInfoDiskSerialNumber OBJECT-TYPE
			SYNTAX OCTET STRING
			MAX-ACCESS read-only
			STATUS current
			DESCRIPTION
				"  "
			::= { hwInfoDiskEntry 15 }

		
		hwInfoDiskLightStatus OBJECT-TYPE
			SYNTAX Unsigned32
			MAX-ACCESS read-only
			STATUS current
			DESCRIPTION
				"  "
			::= { hwInfoDiskEntry 16 }

		
		hwInfoDiskDiskDomainID OBJECT-TYPE
			SYNTAX OCTET STRING
			MAX-ACCESS read-only
			STATUS current
			DESCRIPTION
				" "
			::= { hwInfoDiskEntry 17 }

		
		hwInfoDiskDiskDomainName OBJECT-TYPE
			SYNTAX OCTET STRING
			MAX-ACCESS read-only
			STATUS current
			DESCRIPTION
				"  "
			::= { hwInfoDiskEntry 18 }

		
		hwInfoDiskDiskDomainTierID OBJECT-TYPE
			SYNTAX OCTET STRING
			MAX-ACCESS read-only
			STATUS current
			DESCRIPTION
				"  "
			::= { hwInfoDiskEntry 19 }

		
		hwInfoDiskCofferDisk OBJECT-TYPE
			SYNTAX Unsigned32
			MAX-ACCESS read-only
			STATUS current
			DESCRIPTION
				"  "
			::= { hwInfoDiskEntry 20 }

		
		hwInfoDiskRunTime OBJECT-TYPE
			SYNTAX Unsigned32
			MAX-ACCESS read-only
			STATUS current
			DESCRIPTION
				"  "
			::= { hwInfoDiskEntry 21 }

		
		hwInfoDiskProgress OBJECT-TYPE
			SYNTAX Unsigned32
			MAX-ACCESS read-only
			STATUS current
			DESCRIPTION
				"  "
			::= { hwInfoDiskEntry 22 }

		
		hwInfoDiskBarCode OBJECT-TYPE
			SYNTAX OCTET STRING
			MAX-ACCESS read-only
			STATUS current
			DESCRIPTION
				"  "
			::= { hwInfoDiskEntry 23 }

		
		hwInfoDiskCapacityUsage OBJECT-TYPE
			SYNTAX Unsigned32
			MAX-ACCESS read-only
			STATUS current
			DESCRIPTION
				"  "
			::= { hwInfoDiskEntry 24 }

		
		hwInfoDiskHealthMark OBJECT-TYPE
			SYNTAX Unsigned32
			MAX-ACCESS read-only
			STATUS current
			DESCRIPTION
				"  "
			::= { hwInfoDiskEntry 25 }

		
		hwInfoControllerTable OBJECT-TYPE
			SYNTAX SEQUENCE OF HwInfoControllerEntry
			MAX-ACCESS not-accessible
			STATUS current
			DESCRIPTION
				" "
			::= { hwHardwareInfo 2 }

		
		hwInfoControllerEntry OBJECT-TYPE
			SYNTAX HwInfoControllerEntry
			MAX-ACCESS not-accessible
			STATUS current
			DESCRIPTION
				" "
			INDEX { hwInfoControllerID }
			::= { hwInfoControllerTable 1 }

		
		HwInfoControllerEntry ::=
			SEQUENCE { 
				hwInfoControllerID
					OCTET STRING,
				hwInfoControllerHealthStatus
					Unsigned32,
				hwInfoControllerRunningStatus
					Unsigned32,
				hwInfoControllerCPU
					OCTET STRING,
				hwInfoControllerLocation
					OCTET STRING,
				hwInfoControllerRole
					Unsigned32,
				hwInfoControllerCacheCapacity
					Unsigned32,
				hwInfoControllerCPUUsage
					Unsigned32,
				hwInfoControllerMemoryUsage
					Unsigned32,
				hwInfoControllerVoltage
					Unsigned32,
				hwInfoControllerSoftwareVersion
					OCTET STRING,
				hwInfoControllerPCBVersion
					OCTET STRING,
				hwInfoControllerSESVersion
					OCTET STRING,
				hwInfoControllerBMCVersion
					OCTET STRING,
				hwInfoControllerLogicVersion
					OCTET STRING,
				hwInfoControllerBIOSVersion
					OCTET STRING,
				hwInfoControllerElectronicLabel
					OCTET STRING
			 }

		hwInfoControllerID OBJECT-TYPE
			SYNTAX OCTET STRING
			MAX-ACCESS read-only
			STATUS current
			DESCRIPTION
				"  "
			::= { hwInfoControllerEntry 1 }

		
		hwInfoControllerHealthStatus OBJECT-TYPE
			SYNTAX Unsigned32
			MAX-ACCESS read-only
			STATUS current
			DESCRIPTION
				"  "
			::= { hwInfoControllerEntry 2 }

		
		hwInfoControllerRunningStatus OBJECT-TYPE
			SYNTAX Unsigned32
			MAX-ACCESS read-only
			STATUS current
			DESCRIPTION
				"  "
			::= { hwInfoControllerEntry 3 }

		
		hwInfoControllerCPU OBJECT-TYPE
			SYNTAX OCTET STRING
			MAX-ACCESS read-only
			STATUS current
			DESCRIPTION
				"  "
			::= { hwInfoControllerEntry 4 }

		
		hwInfoControllerLocation OBJECT-TYPE
			SYNTAX OCTET STRING
			MAX-ACCESS read-only
			STATUS current
			DESCRIPTION
				"  "
			::= { hwInfoControllerEntry 5 }

		
		hwInfoControllerRole OBJECT-TYPE
			SYNTAX Unsigned32
			MAX-ACCESS read-only
			STATUS current
			DESCRIPTION
				"  "
			::= { hwInfoControllerEntry 6 }

		
		hwInfoControllerCacheCapacity OBJECT-TYPE
			SYNTAX Unsigned32
			MAX-ACCESS read-only
			STATUS current
			DESCRIPTION
				"  "
			::= { hwInfoControllerEntry 7 }

		
		hwInfoControllerCPUUsage OBJECT-TYPE
			SYNTAX Unsigned32
			MAX-ACCESS read-only
			STATUS current
			DESCRIPTION
				"  "
			::= { hwInfoControllerEntry 8 }

		
		hwInfoControllerMemoryUsage OBJECT-TYPE
			SYNTAX Unsigned32
			MAX-ACCESS read-only
			STATUS current
			DESCRIPTION
				"  "
			::= { hwInfoControllerEntry 9 }

		
		hwInfoControllerVoltage OBJECT-TYPE
			SYNTAX Unsigned32
			MAX-ACCESS read-only
			STATUS current
			DESCRIPTION
				"  "
			::= { hwInfoControllerEntry 10 }

		
		hwInfoControllerSoftwareVersion OBJECT-TYPE
			SYNTAX OCTET STRING
			MAX-ACCESS read-only
			STATUS current
			DESCRIPTION
				"  "
			::= { hwInfoControllerEntry 11 }

		
		hwInfoControllerPCBVersion OBJECT-TYPE
			SYNTAX OCTET STRING
			MAX-ACCESS read-only
			STATUS current
			DESCRIPTION
				"  "
			::= { hwInfoControllerEntry 12 }

		
		hwInfoControllerSESVersion OBJECT-TYPE
			SYNTAX OCTET STRING
			MAX-ACCESS read-only
			STATUS current
			DESCRIPTION
				"  "
			::= { hwInfoControllerEntry 13 }

		
		hwInfoControllerBMCVersion OBJECT-TYPE
			SYNTAX OCTET STRING
			MAX-ACCESS read-only
			STATUS current
			DESCRIPTION
				"  "
			::= { hwInfoControllerEntry 14 }

		
		hwInfoControllerLogicVersion OBJECT-TYPE
			SYNTAX OCTET STRING
			MAX-ACCESS read-only
			STATUS current
			DESCRIPTION
				"  "
			::= { hwInfoControllerEntry 15 }

		
		hwInfoControllerBIOSVersion OBJECT-TYPE
			SYNTAX OCTET STRING
			MAX-ACCESS read-only
			STATUS current
			DESCRIPTION
				"  "
			::= { hwInfoControllerEntry 16 }

		
		hwInfoControllerElectronicLabel OBJECT-TYPE
			SYNTAX OCTET STRING
			MAX-ACCESS read-only
			STATUS current
			DESCRIPTION
				"  "
			::= { hwInfoControllerEntry 17 }

		
		hwInfoPowerTable OBJECT-TYPE
			SYNTAX SEQUENCE OF HwInfoPowerEntry
			MAX-ACCESS not-accessible
			STATUS current
			DESCRIPTION
				" "
			::= { hwHardwareInfo 3 }

		
		hwInfoPowerEntry OBJECT-TYPE
			SYNTAX HwInfoPowerEntry
			MAX-ACCESS not-accessible
			STATUS current
			DESCRIPTION
				"  "
			INDEX { hwInfoPowerID }
			::= { hwInfoPowerTable 1 }

		
		HwInfoPowerEntry ::=
			SEQUENCE { 
				hwInfoPowerID
					OCTET STRING,
				hwInfoPowerLocation
					OCTET STRING,
				hwInfoPowerHealthStatus
					Unsigned32,
				hwInfoPowerRunningStatus
					Unsigned32,
				hwInfoPowerType
					Unsigned32,
				hwInfoPowerManufacturer
					OCTET STRING,
				hwInfoPowerModle
					OCTET STRING,
				hwInfoPowerVersion
					OCTET STRING,
				hwInfoPowerProduceDate
					OCTET STRING,
				hwInfoPowerSerialNumber
					OCTET STRING
			 }

		hwInfoPowerID OBJECT-TYPE
			SYNTAX OCTET STRING
			MAX-ACCESS read-only
			STATUS current
			DESCRIPTION
				"  "
			::= { hwInfoPowerEntry 1 }

		
		hwInfoPowerLocation OBJECT-TYPE
			SYNTAX OCTET STRING
			MAX-ACCESS read-only
			STATUS current
			DESCRIPTION
				"  "
			::= { hwInfoPowerEntry 2 }

		
		hwInfoPowerHealthStatus OBJECT-TYPE
			SYNTAX Unsigned32
			MAX-ACCESS read-only
			STATUS current
			DESCRIPTION
				"  "
			::= { hwInfoPowerEntry 3 }

		
		hwInfoPowerRunningStatus OBJECT-TYPE
			SYNTAX Unsigned32
			MAX-ACCESS read-only
			STATUS current
			DESCRIPTION
				"  "
			::= { hwInfoPowerEntry 4 }

		
		hwInfoPowerType OBJECT-TYPE
			SYNTAX Unsigned32
			MAX-ACCESS read-only
			STATUS current
			DESCRIPTION
				"  "
			::= { hwInfoPowerEntry 5 }

		
		hwInfoPowerManufacturer OBJECT-TYPE
			SYNTAX OCTET STRING
			MAX-ACCESS read-only
			STATUS current
			DESCRIPTION
				"  "
			::= { hwInfoPowerEntry 6 }

		
		hwInfoPowerModle OBJECT-TYPE
			SYNTAX OCTET STRING
			MAX-ACCESS read-only
			STATUS current
			DESCRIPTION
				"  "
			::= { hwInfoPowerEntry 7 }

		
		hwInfoPowerVersion OBJECT-TYPE
			SYNTAX OCTET STRING
			MAX-ACCESS read-only
			STATUS current
			DESCRIPTION
				"  "
			::= { hwInfoPowerEntry 8 }

		
		hwInfoPowerProduceDate OBJECT-TYPE
			SYNTAX OCTET STRING
			MAX-ACCESS read-only
			STATUS current
			DESCRIPTION
				"  "
			::= { hwInfoPowerEntry 9 }

		
		hwInfoPowerSerialNumber OBJECT-TYPE
			SYNTAX OCTET STRING
			MAX-ACCESS read-only
			STATUS current
			DESCRIPTION
				"  "
			::= { hwInfoPowerEntry 10 }

		
		hwInfoFanTable OBJECT-TYPE
			SYNTAX SEQUENCE OF HwInfoFanEntry
			MAX-ACCESS not-accessible
			STATUS current
			DESCRIPTION
				" "
			::= { hwHardwareInfo 4 }

		
		hwInfoFanEntry OBJECT-TYPE
			SYNTAX HwInfoFanEntry
			MAX-ACCESS not-accessible
			STATUS current
			DESCRIPTION
				" "
			INDEX { hwInfoFanID }
			::= { hwInfoFanTable 1 }

		
		HwInfoFanEntry ::=
			SEQUENCE { 
				hwInfoFanID
					OCTET STRING,
				hwInfoFanLocation
					OCTET STRING,
				hwInfoFanHealthStatus
					Unsigned32,
				hwInfoFanRunningStatus
					Unsigned32,
				hwInfoFanRunningLevel
					Unsigned32,
				hwInfoFanElectronicLabel
					OCTET STRING
			 }

		hwInfoFanID OBJECT-TYPE
			SYNTAX OCTET STRING
			MAX-ACCESS read-only
			STATUS current
			DESCRIPTION
				"  "
			::= { hwInfoFanEntry 1 }

		
		hwInfoFanLocation OBJECT-TYPE
			SYNTAX OCTET STRING
			MAX-ACCESS read-only
			STATUS current
			DESCRIPTION
				"  "
			::= { hwInfoFanEntry 2 }

		
		hwInfoFanHealthStatus OBJECT-TYPE
			SYNTAX Unsigned32
			MAX-ACCESS read-only
			STATUS current
			DESCRIPTION
				"  "
			::= { hwInfoFanEntry 3 }

		
		hwInfoFanRunningStatus OBJECT-TYPE
			SYNTAX Unsigned32
			MAX-ACCESS read-only
			STATUS current
			DESCRIPTION
				"  "
			::= { hwInfoFanEntry 4 }

		
		hwInfoFanRunningLevel OBJECT-TYPE
			SYNTAX Unsigned32
			MAX-ACCESS read-only
			STATUS current
			DESCRIPTION
				"  "
			::= { hwInfoFanEntry 5 }

		
		hwInfoFanElectronicLabel OBJECT-TYPE
			SYNTAX OCTET STRING
			MAX-ACCESS read-only
			STATUS current
			DESCRIPTION
				"  "
			::= { hwInfoFanEntry 6 }

		
		hwInfoBBUTable OBJECT-TYPE
			SYNTAX SEQUENCE OF HwInfoBBUEntry
			MAX-ACCESS not-accessible
			STATUS current
			DESCRIPTION
				" "
			::= { hwHardwareInfo 5 }

		
		hwInfoBBUEntry OBJECT-TYPE
			SYNTAX HwInfoBBUEntry
			MAX-ACCESS not-accessible
			STATUS current
			DESCRIPTION
				" "
			INDEX { hwInfoBBUID }
			::= { hwInfoBBUTable 1 }

		
		HwInfoBBUEntry ::=
			SEQUENCE { 
				hwInfoBBUID
					OCTET STRING,
				hwInfoBBULocation
					OCTET STRING,
				hwInfoBBUHealthStatus
					Unsigned32,
				hwInfoBBURunningStatus
					Unsigned32,
				hwInfoBBUType
					Unsigned32,
				hwInfoBBUCurrentVoltage
					Unsigned32,
				hwInfoBBUNumberOfDischarges
					Unsigned32,
				hwInfoBBUFirmwareVersion
					OCTET STRING,
				hwInfoBBUDeliveredOn
					OCTET STRING,
				hwInfoBBUOwningController
					OCTET STRING,
				hwInfoBBUElectronicLabel
					OCTET STRING
			 }

		hwInfoBBUID OBJECT-TYPE
			SYNTAX OCTET STRING
			MAX-ACCESS read-only
			STATUS current
			DESCRIPTION
				"  "
			::= { hwInfoBBUEntry 1 }

		
		hwInfoBBULocation OBJECT-TYPE
			SYNTAX OCTET STRING
			MAX-ACCESS read-only
			STATUS current
			DESCRIPTION
				"  "
			::= { hwInfoBBUEntry 2 }

		
		hwInfoBBUHealthStatus OBJECT-TYPE
			SYNTAX Unsigned32
			MAX-ACCESS read-only
			STATUS current
			DESCRIPTION
				"  "
			::= { hwInfoBBUEntry 3 }

		
		hwInfoBBURunningStatus OBJECT-TYPE
			SYNTAX Unsigned32
			MAX-ACCESS read-only
			STATUS current
			DESCRIPTION
				"  "
			::= { hwInfoBBUEntry 4 }

		
		hwInfoBBUType OBJECT-TYPE
			SYNTAX Unsigned32
			MAX-ACCESS read-only
			STATUS current
			DESCRIPTION
				"  "
			::= { hwInfoBBUEntry 5 }

		
		hwInfoBBUCurrentVoltage OBJECT-TYPE
			SYNTAX Unsigned32
			MAX-ACCESS read-only
			STATUS current
			DESCRIPTION
				"  "
			::= { hwInfoBBUEntry 6 }

		
		hwInfoBBUNumberOfDischarges OBJECT-TYPE
			SYNTAX Unsigned32
			MAX-ACCESS read-only
			STATUS current
			DESCRIPTION
				"  "
			::= { hwInfoBBUEntry 7 }

		
		hwInfoBBUFirmwareVersion OBJECT-TYPE
			SYNTAX OCTET STRING
			MAX-ACCESS read-only
			STATUS current
			DESCRIPTION
				"  "
			::= { hwInfoBBUEntry 8 }

		
		hwInfoBBUDeliveredOn OBJECT-TYPE
			SYNTAX OCTET STRING
			MAX-ACCESS read-only
			STATUS current
			DESCRIPTION
				"  "
			::= { hwInfoBBUEntry 9 }

		
		hwInfoBBUOwningController OBJECT-TYPE
			SYNTAX OCTET STRING
			MAX-ACCESS read-only
			STATUS current
			DESCRIPTION
				"  "
			::= { hwInfoBBUEntry 10 }

		
		hwInfoBBUElectronicLabel OBJECT-TYPE
			SYNTAX OCTET STRING
			MAX-ACCESS read-only
			STATUS current
			DESCRIPTION
				"  "
			::= { hwInfoBBUEntry 11 }

		
		hwInfoEnclosureTable OBJECT-TYPE
			SYNTAX SEQUENCE OF HwInfoEnclosureEntry
			MAX-ACCESS not-accessible
			STATUS current
			DESCRIPTION
				" "
			::= { hwHardwareInfo 6 }

		
		hwInfoEnclosureEntry OBJECT-TYPE
			SYNTAX HwInfoEnclosureEntry
			MAX-ACCESS not-accessible
			STATUS current
			DESCRIPTION
				" "
			INDEX { hwInfoEnclosureID }
			::= { hwInfoEnclosureTable 1 }

		
		HwInfoEnclosureEntry ::=
			SEQUENCE { 
				hwInfoEnclosureID
					OCTET STRING,
				hwInfoEnclosureName
					OCTET STRING,
				hwInfoEnclosureLogicType
					Unsigned32,
				hwInfoEnclosureHealthStatus
					Unsigned32,
				hwInfoEnclosureRunningStatus
					Unsigned32,
				hwInfoEnclosureLocation
					OCTET STRING,
				hwInfoEnclosureType
					Unsigned32,
				hwInfoEnclosureTemperature
					Integer32,
				hwInfoEnclosureSN
					OCTET STRING,
				hwInfoEnclosureMAC
					OCTET STRING,
				hwInfoEnclosureHeight
					Unsigned32,
				hwInfoEnclosureExpansionDepth
					Unsigned32,
				hwInfoEnclosureElectronicLabel
					OCTET STRING
			 }

		hwInfoEnclosureID OBJECT-TYPE
			SYNTAX OCTET STRING
			MAX-ACCESS read-only
			STATUS current
			DESCRIPTION
				" "
			::= { hwInfoEnclosureEntry 1 }

		
		hwInfoEnclosureName OBJECT-TYPE
			SYNTAX OCTET STRING
			MAX-ACCESS read-only
			STATUS current
			DESCRIPTION
				" "
			::= { hwInfoEnclosureEntry 2 }

		
		hwInfoEnclosureLogicType OBJECT-TYPE
			SYNTAX Unsigned32
			MAX-ACCESS read-only
			STATUS current
			DESCRIPTION
				" "
			::= { hwInfoEnclosureEntry 3 }

		
		hwInfoEnclosureHealthStatus OBJECT-TYPE
			SYNTAX Unsigned32
			MAX-ACCESS read-only
			STATUS current
			DESCRIPTION
				" "
			::= { hwInfoEnclosureEntry 4 }

		
		hwInfoEnclosureRunningStatus OBJECT-TYPE
			SYNTAX Unsigned32
			MAX-ACCESS read-only
			STATUS current
			DESCRIPTION
				" "
			::= { hwInfoEnclosureEntry 5 }

		
		hwInfoEnclosureLocation OBJECT-TYPE
			SYNTAX OCTET STRING
			MAX-ACCESS read-only
			STATUS current
			DESCRIPTION
				" "
			::= { hwInfoEnclosureEntry 6 }

		
		hwInfoEnclosureType OBJECT-TYPE
			SYNTAX Unsigned32
			MAX-ACCESS read-only
			STATUS current
			DESCRIPTION
				" "
			::= { hwInfoEnclosureEntry 7 }

		
		hwInfoEnclosureTemperature OBJECT-TYPE
			SYNTAX Integer32
			MAX-ACCESS read-only
			STATUS current
			DESCRIPTION
				" "
			::= { hwInfoEnclosureEntry 8 }

		
		hwInfoEnclosureSN OBJECT-TYPE
			SYNTAX OCTET STRING
			MAX-ACCESS read-only
			STATUS current
			DESCRIPTION
				" "
			::= { hwInfoEnclosureEntry 9 }

		
		hwInfoEnclosureMAC OBJECT-TYPE
			SYNTAX OCTET STRING
			MAX-ACCESS read-only
			STATUS current
			DESCRIPTION
				" "
			::= { hwInfoEnclosureEntry 10 }

		
		hwInfoEnclosureHeight OBJECT-TYPE
			SYNTAX Unsigned32
			MAX-ACCESS read-only
			STATUS current
			DESCRIPTION
				" "
			::= { hwInfoEnclosureEntry 11 }

		
		hwInfoEnclosureExpansionDepth OBJECT-TYPE
			SYNTAX Unsigned32
			MAX-ACCESS read-only
			STATUS current
			DESCRIPTION
				" "
			::= { hwInfoEnclosureEntry 12 }

		
		hwInfoEnclosureElectronicLabel OBJECT-TYPE
			SYNTAX OCTET STRING
			MAX-ACCESS read-only
			STATUS current
			DESCRIPTION
				" "
			::= { hwInfoEnclosureEntry 13 }

		
		hwInfoPortComTable OBJECT-TYPE
			SYNTAX SEQUENCE OF HwInfoPortComEntry
			MAX-ACCESS not-accessible
			STATUS current
			DESCRIPTION
				" "
			::= { hwHardwareInfo 7 }

		
		hwInfoPortComEntry OBJECT-TYPE
			SYNTAX HwInfoPortComEntry
			MAX-ACCESS not-accessible
			STATUS current
			DESCRIPTION
				" "
			INDEX { hwInfoPortComID }
			::= { hwInfoPortComTable 1 }

		
		HwInfoPortComEntry ::=
			SEQUENCE { 
				hwInfoPortComID
					OCTET STRING,
				hwInfoPortComLocation
					OCTET STRING,
				hwInfoPortComHealthStatus
					Unsigned32,
				hwInfoPortComRunningStatus
					Unsigned32,
				hwInfoPortComType
					Unsigned32
			 }

		hwInfoPortComID OBJECT-TYPE
			SYNTAX OCTET STRING
			MAX-ACCESS read-only
			STATUS current
			DESCRIPTION
				" "
			::= { hwInfoPortComEntry 1 }

		
		hwInfoPortComLocation OBJECT-TYPE
			SYNTAX OCTET STRING
			MAX-ACCESS read-only
			STATUS current
			DESCRIPTION
				" "
			::= { hwInfoPortComEntry 2 }

		
		hwInfoPortComHealthStatus OBJECT-TYPE
			SYNTAX Unsigned32
			MAX-ACCESS read-only
			STATUS current
			DESCRIPTION
				" "
			::= { hwInfoPortComEntry 3 }

		
		hwInfoPortComRunningStatus OBJECT-TYPE
			SYNTAX Unsigned32
			MAX-ACCESS read-only
			STATUS current
			DESCRIPTION
				" "
			::= { hwInfoPortComEntry 4 }

		
		hwInfoPortComType OBJECT-TYPE
			SYNTAX Unsigned32
			MAX-ACCESS read-only
			STATUS current
			DESCRIPTION
				" "
			::= { hwInfoPortComEntry 5 }

		
		hwInfoPortEthTable OBJECT-TYPE
			SYNTAX SEQUENCE OF HwInfoPortEthEntry
			MAX-ACCESS not-accessible
			STATUS current
			DESCRIPTION
				" "
			::= { hwHardwareInfo 8 }

		
		hwInfoPortEthEntry OBJECT-TYPE
			SYNTAX HwInfoPortEthEntry
			MAX-ACCESS not-accessible
			STATUS current
			DESCRIPTION
				" "
			INDEX { hwInfoPortEthID }
			::= { hwInfoPortEthTable 1 }

		
		HwInfoPortEthEntry ::=
			SEQUENCE { 
				hwInfoPortEthID
					OCTET STRING,
				hwInfoPortEthLocation
					OCTET STRING,
				hwInfoPortEthHealthStatus
					Unsigned32,
				hwInfoPortEthRunningStatus
					Unsigned32,
				hwInfoPortEthType
					Unsigned32,
				hwInfoPortEthIPv4Address
					OCTET STRING,
				hwInfoPortEthSubnetMask
					OCTET STRING,
				hwInfoPortEthIPv4Gateway
					OCTET STRING,
				hwInfoPortEthIPv6Address
					OCTET STRING,
				hwInfoPortEthIPv6PrefixLength
					OCTET STRING,
				hwInfoPortEthIPv6Gateway
					OCTET STRING,
				hwInfoPortEthMAC
					OCTET STRING,
				hwInfoPortEthRole
					Unsigned32,
				hwInfoPortEthMode
					Unsigned32,
				hwInfoPortEthMTU
					Unsigned32,
				hwInfoPortEthWorkingRate
					Unsigned32,
				hwInfoPortEthBondName
					OCTET STRING,
				hwInfoPortEthiSCSIPort
					OCTET STRING,
				hwInfoPortEthiSCSIName
					OCTET STRING,
				hwInfoPortEthErrorPackets
					Unsigned32,
				hwInfoPortEthLostPackages
					Unsigned32,
				hwInfoPortEthStartTime
					OCTET STRING
			 }

		hwInfoPortEthID OBJECT-TYPE
			SYNTAX OCTET STRING
			MAX-ACCESS read-only
			STATUS current
			DESCRIPTION
				" "
			::= { hwInfoPortEthEntry 1 }

		
		hwInfoPortEthLocation OBJECT-TYPE
			SYNTAX OCTET STRING
			MAX-ACCESS read-only
			STATUS current
			DESCRIPTION
				" "
			::= { hwInfoPortEthEntry 2 }

		
		hwInfoPortEthHealthStatus OBJECT-TYPE
			SYNTAX Unsigned32
			MAX-ACCESS read-only
			STATUS current
			DESCRIPTION
				" "
			::= { hwInfoPortEthEntry 3 }

		
		hwInfoPortEthRunningStatus OBJECT-TYPE
			SYNTAX Unsigned32
			MAX-ACCESS read-only
			STATUS current
			DESCRIPTION
				" "
			::= { hwInfoPortEthEntry 4 }

		
		hwInfoPortEthType OBJECT-TYPE
			SYNTAX Unsigned32
			MAX-ACCESS read-only
			STATUS current
			DESCRIPTION
				" "
			::= { hwInfoPortEthEntry 5 }

		
		hwInfoPortEthIPv4Address OBJECT-TYPE
			SYNTAX OCTET STRING
			MAX-ACCESS read-only
			STATUS current
			DESCRIPTION
				"  "
			::= { hwInfoPortEthEntry 6 }

		
		hwInfoPortEthSubnetMask OBJECT-TYPE
			SYNTAX OCTET STRING
			MAX-ACCESS read-only
			STATUS current
			DESCRIPTION
				"  "
			::= { hwInfoPortEthEntry 7 }

		
		hwInfoPortEthIPv4Gateway OBJECT-TYPE
			SYNTAX OCTET STRING
			MAX-ACCESS read-only
			STATUS current
			DESCRIPTION
				"  "
			::= { hwInfoPortEthEntry 8 }

		
		hwInfoPortEthIPv6Address OBJECT-TYPE
			SYNTAX OCTET STRING
			MAX-ACCESS read-only
			STATUS current
			DESCRIPTION
				" "
			::= { hwInfoPortEthEntry 9 }

		
		hwInfoPortEthIPv6PrefixLength OBJECT-TYPE
			SYNTAX OCTET STRING
			MAX-ACCESS read-only
			STATUS current
			DESCRIPTION
				" "
			::= { hwInfoPortEthEntry 10 }

		
		hwInfoPortEthIPv6Gateway OBJECT-TYPE
			SYNTAX OCTET STRING
			MAX-ACCESS read-only
			STATUS current
			DESCRIPTION
				" "
			::= { hwInfoPortEthEntry 11 }

		
		hwInfoPortEthMAC OBJECT-TYPE
			SYNTAX OCTET STRING
			MAX-ACCESS read-only
			STATUS current
			DESCRIPTION
				" "
			::= { hwInfoPortEthEntry 12 }

		
		hwInfoPortEthRole OBJECT-TYPE
			SYNTAX Unsigned32
			MAX-ACCESS read-only
			STATUS current
			DESCRIPTION
				" "
			::= { hwInfoPortEthEntry 13 }

		
		hwInfoPortEthMode OBJECT-TYPE
			SYNTAX Unsigned32
			MAX-ACCESS read-only
			STATUS current
			DESCRIPTION
				"  "
			::= { hwInfoPortEthEntry 14 }

		
		hwInfoPortEthMTU OBJECT-TYPE
			SYNTAX Unsigned32
			MAX-ACCESS read-only
			STATUS current
			DESCRIPTION
				" "
			::= { hwInfoPortEthEntry 15 }

		
		hwInfoPortEthWorkingRate OBJECT-TYPE
			SYNTAX Unsigned32
			MAX-ACCESS read-only
			STATUS current
			DESCRIPTION
				" "
			::= { hwInfoPortEthEntry 16 }

		
		hwInfoPortEthBondName OBJECT-TYPE
			SYNTAX OCTET STRING
			MAX-ACCESS read-only
			STATUS current
			DESCRIPTION
				" "
			::= { hwInfoPortEthEntry 17 }

		
		hwInfoPortEthiSCSIPort OBJECT-TYPE
			SYNTAX OCTET STRING
			MAX-ACCESS read-only
			STATUS current
			DESCRIPTION
				"  "
			::= { hwInfoPortEthEntry 18 }

		
		hwInfoPortEthiSCSIName OBJECT-TYPE
			SYNTAX OCTET STRING
			MAX-ACCESS read-only
			STATUS current
			DESCRIPTION
				"  "
			::= { hwInfoPortEthEntry 19 }

		
		hwInfoPortEthErrorPackets OBJECT-TYPE
			SYNTAX Unsigned32
			MAX-ACCESS read-only
			STATUS current
			DESCRIPTION
				"  "
			::= { hwInfoPortEthEntry 20 }

		
		hwInfoPortEthLostPackages OBJECT-TYPE
			SYNTAX Unsigned32
			MAX-ACCESS read-only
			STATUS current
			DESCRIPTION
				" "
			::= { hwInfoPortEthEntry 21 }

		
		hwInfoPortEthStartTime OBJECT-TYPE
			SYNTAX OCTET STRING
			MAX-ACCESS read-only
			STATUS current
			DESCRIPTION
				" "
			::= { hwInfoPortEthEntry 22 }

		
		hwInfoPortFCTable OBJECT-TYPE
			SYNTAX SEQUENCE OF HwInfoPortFCEntry
			MAX-ACCESS not-accessible
			STATUS current
			DESCRIPTION
				" "
			::= { hwHardwareInfo 9 }

		
		hwInfoPortFCEntry OBJECT-TYPE
			SYNTAX HwInfoPortFCEntry
			MAX-ACCESS not-accessible
			STATUS current
			DESCRIPTION
				" "
			INDEX { hwInfoPortFCID }
			::= { hwInfoPortFCTable 1 }

		
		HwInfoPortFCEntry ::=
			SEQUENCE { 
				hwInfoPortFCID
					OCTET STRING,
				hwInfoPortFCLocation
					OCTET STRING,
				hwInfoPortFCHealthStatus
					Unsigned32,
				hwInfoPortFCRunningStatus
					Unsigned32,
				hwInfoPortFCType
					Unsigned32,
				hwInfoPortFCWorkingRate
					Unsigned32,
				hwInfoPortFCConfiguredSpeed
					Unsigned32,
				hwInfoPortFCWWN
					OCTET STRING,
				hwInfoPortFCRole
					Unsigned32,
				hwInfoPortFCSFPStatus
					Unsigned32,
				hwInfoPortFCWorkingMode
					Unsigned32,
				hwInfoPortFCConfiguredMode
					Unsigned32,
				hwInfoPortFCFloginDelayTimes
					Unsigned32,
				hwInfoPortFCLostSignals
					Unsigned32,
				hwInfoPortFCLinkErrorsCodes
					Unsigned32,
				hwInfoPortFCLostSynchronizations
					Unsigned32,
				hwInfoPortFCFailedConnections
					Unsigned32,
				hwInfoPortFCStartTime
					OCTET STRING
			 }

		hwInfoPortFCID OBJECT-TYPE
			SYNTAX OCTET STRING
			MAX-ACCESS read-only
			STATUS current
			DESCRIPTION
				" "
			::= { hwInfoPortFCEntry 1 }

		
		hwInfoPortFCLocation OBJECT-TYPE
			SYNTAX OCTET STRING
			MAX-ACCESS read-only
			STATUS current
			DESCRIPTION
				" "
			::= { hwInfoPortFCEntry 2 }

		
		hwInfoPortFCHealthStatus OBJECT-TYPE
			SYNTAX Unsigned32
			MAX-ACCESS read-only
			STATUS current
			DESCRIPTION
				" "
			::= { hwInfoPortFCEntry 3 }

		
		hwInfoPortFCRunningStatus OBJECT-TYPE
			SYNTAX Unsigned32
			MAX-ACCESS read-only
			STATUS current
			DESCRIPTION
				" "
			::= { hwInfoPortFCEntry 4 }

		
		hwInfoPortFCType OBJECT-TYPE
			SYNTAX Unsigned32
			MAX-ACCESS read-only
			STATUS current
			DESCRIPTION
				" "
			::= { hwInfoPortFCEntry 5 }

		
		hwInfoPortFCWorkingRate OBJECT-TYPE
			SYNTAX Unsigned32
			MAX-ACCESS read-only
			STATUS current
			DESCRIPTION
				" "
			::= { hwInfoPortFCEntry 6 }

		
		hwInfoPortFCConfiguredSpeed OBJECT-TYPE
			SYNTAX Unsigned32
			MAX-ACCESS read-only
			STATUS current
			DESCRIPTION
				" "
			::= { hwInfoPortFCEntry 7 }

		
		hwInfoPortFCWWN OBJECT-TYPE
			SYNTAX OCTET STRING
			MAX-ACCESS read-only
			STATUS current
			DESCRIPTION
				" "
			::= { hwInfoPortFCEntry 8 }

		
		hwInfoPortFCRole OBJECT-TYPE
			SYNTAX Unsigned32
			MAX-ACCESS read-only
			STATUS current
			DESCRIPTION
				" "
			::= { hwInfoPortFCEntry 9 }

		
		hwInfoPortFCSFPStatus OBJECT-TYPE
			SYNTAX Unsigned32
			MAX-ACCESS read-only
			STATUS current
			DESCRIPTION
				" "
			::= { hwInfoPortFCEntry 10 }

		
		hwInfoPortFCWorkingMode OBJECT-TYPE
			SYNTAX Unsigned32
			MAX-ACCESS read-only
			STATUS current
			DESCRIPTION
				" "
			::= { hwInfoPortFCEntry 11 }

		
		hwInfoPortFCConfiguredMode OBJECT-TYPE
			SYNTAX Unsigned32
			MAX-ACCESS read-only
			STATUS current
			DESCRIPTION
				" "
			::= { hwInfoPortFCEntry 12 }

		
		hwInfoPortFCFloginDelayTimes OBJECT-TYPE
			SYNTAX Unsigned32
			MAX-ACCESS read-only
			STATUS current
			DESCRIPTION
				" "
			::= { hwInfoPortFCEntry 13 }

		
		hwInfoPortFCLostSignals OBJECT-TYPE
			SYNTAX Unsigned32
			MAX-ACCESS read-only
			STATUS current
			DESCRIPTION
				" "
			::= { hwInfoPortFCEntry 14 }

		
		hwInfoPortFCLinkErrorsCodes OBJECT-TYPE
			SYNTAX Unsigned32
			MAX-ACCESS read-only
			STATUS current
			DESCRIPTION
				" "
			::= { hwInfoPortFCEntry 15 }

		
		hwInfoPortFCLostSynchronizations OBJECT-TYPE
			SYNTAX Unsigned32
			MAX-ACCESS read-only
			STATUS current
			DESCRIPTION
				" "
			::= { hwInfoPortFCEntry 16 }

		
		hwInfoPortFCFailedConnections OBJECT-TYPE
			SYNTAX Unsigned32
			MAX-ACCESS read-only
			STATUS current
			DESCRIPTION
				" "
			::= { hwInfoPortFCEntry 17 }

		
		hwInfoPortFCStartTime OBJECT-TYPE
			SYNTAX OCTET STRING
			MAX-ACCESS read-only
			STATUS current
			DESCRIPTION
				" "
			::= { hwInfoPortFCEntry 18 }

		
		hwInfoPortFCoETable OBJECT-TYPE
			SYNTAX SEQUENCE OF HwInfoPortFCoEEntry
			MAX-ACCESS not-accessible
			STATUS current
			DESCRIPTION
				" "
			::= { hwHardwareInfo 10 }

		
		hwInfoPortFCoEEntry OBJECT-TYPE
			SYNTAX HwInfoPortFCoEEntry
			MAX-ACCESS not-accessible
			STATUS current
			DESCRIPTION
				" "
			INDEX { hwInfoPortFCoEID }
			::= { hwInfoPortFCoETable 1 }

		
		HwInfoPortFCoEEntry ::=
			SEQUENCE { 
				hwInfoPortFCoEID
					OCTET STRING,
				hwInfoPortFCoELocation
					OCTET STRING,
				hwInfoPortFCoEHealthStatus
					Unsigned32,
				hwInfoPortFCoERunningStatus
					Unsigned32,
				hwInfoPortFCoEType
					Unsigned32,
				hwInfoPortFCoEWorkingRate
					Unsigned32,
				hwInfoPortFCoEWWN
					OCTET STRING,
				hwInfoPortFCoERole
					Unsigned32,
				hwInfoPortFCoESFPStatus
					Unsigned32,
				hwInfoPortFCoEErrorPackets
					Unsigned32,
				hwInfoPortFCoELostPackets
					Unsigned32,
				hwInfoPortFCoEOverFlowedPackets
					Unsigned32,
				hwInfoPortFCoEStartTime
					OCTET STRING
			 }

		hwInfoPortFCoEID OBJECT-TYPE
			SYNTAX OCTET STRING
			MAX-ACCESS read-only
			STATUS current
			DESCRIPTION
				"  "
			::= { hwInfoPortFCoEEntry 1 }

		
		hwInfoPortFCoELocation OBJECT-TYPE
			SYNTAX OCTET STRING
			MAX-ACCESS read-only
			STATUS current
			DESCRIPTION
				"  "
			::= { hwInfoPortFCoEEntry 2 }

		
		hwInfoPortFCoEHealthStatus OBJECT-TYPE
			SYNTAX Unsigned32
			MAX-ACCESS read-only
			STATUS current
			DESCRIPTION
				" "
			::= { hwInfoPortFCoEEntry 3 }

		
		hwInfoPortFCoERunningStatus OBJECT-TYPE
			SYNTAX Unsigned32
			MAX-ACCESS read-only
			STATUS current
			DESCRIPTION
				" "
			::= { hwInfoPortFCoEEntry 4 }

		
		hwInfoPortFCoEType OBJECT-TYPE
			SYNTAX Unsigned32
			MAX-ACCESS read-only
			STATUS current
			DESCRIPTION
				" "
			::= { hwInfoPortFCoEEntry 5 }

		
		hwInfoPortFCoEWorkingRate OBJECT-TYPE
			SYNTAX Unsigned32
			MAX-ACCESS read-only
			STATUS current
			DESCRIPTION
				"  "
			::= { hwInfoPortFCoEEntry 6 }

		
		hwInfoPortFCoEWWN OBJECT-TYPE
			SYNTAX OCTET STRING
			MAX-ACCESS read-only
			STATUS current
			DESCRIPTION
				"  "
			::= { hwInfoPortFCoEEntry 7 }

		
		hwInfoPortFCoERole OBJECT-TYPE
			SYNTAX Unsigned32
			MAX-ACCESS read-only
			STATUS current
			DESCRIPTION
				" "
			::= { hwInfoPortFCoEEntry 8 }

		
		hwInfoPortFCoESFPStatus OBJECT-TYPE
			SYNTAX Unsigned32
			MAX-ACCESS read-only
			STATUS current
			DESCRIPTION
				"  "
			::= { hwInfoPortFCoEEntry 9 }

		
		hwInfoPortFCoEErrorPackets OBJECT-TYPE
			SYNTAX Unsigned32
			MAX-ACCESS read-only
			STATUS current
			DESCRIPTION
				" "
			::= { hwInfoPortFCoEEntry 10 }

		
		hwInfoPortFCoELostPackets OBJECT-TYPE
			SYNTAX Unsigned32
			MAX-ACCESS read-only
			STATUS current
			DESCRIPTION
				"  "
			::= { hwInfoPortFCoEEntry 11 }

		
		hwInfoPortFCoEOverFlowedPackets OBJECT-TYPE
			SYNTAX Unsigned32
			MAX-ACCESS read-only
			STATUS current
			DESCRIPTION
				" "
			::= { hwInfoPortFCoEEntry 12 }

		
		hwInfoPortFCoEStartTime OBJECT-TYPE
			SYNTAX OCTET STRING
			MAX-ACCESS read-only
			STATUS current
			DESCRIPTION
				"  "
			::= { hwInfoPortFCoEEntry 13 }

		
		hwInfoPortPCIETable OBJECT-TYPE
			SYNTAX SEQUENCE OF HwInfoPortPCIEEntry
			MAX-ACCESS not-accessible
			STATUS current
			DESCRIPTION
				" "
			::= { hwHardwareInfo 11 }

		
		hwInfoPortPCIEEntry OBJECT-TYPE
			SYNTAX HwInfoPortPCIEEntry
			MAX-ACCESS not-accessible
			STATUS current
			DESCRIPTION
				" "
			INDEX { hwInfoPortPCIEID }
			::= { hwInfoPortPCIETable 1 }

		
		HwInfoPortPCIEEntry ::=
			SEQUENCE { 
				hwInfoPortPCIEID
					OCTET STRING,
				hwInfoPortPCIELocation
					OCTET STRING,
				hwInfoPortPCIEHealthStatus
					Unsigned32,
				hwInfoPortPCIERunningStatus
					Unsigned32,
				hwInfoPortPCIESpeed
					Unsigned32,
				hwInfoPortPCIECurrentPeerPortID
					OCTET STRING,
				hwInfoPortPCIESuggestPeerPortID
					OCTET STRING,
				hwInfoPortPCIELostSignals
					Unsigned32,
				hwInfoPortPCIEECRCError
					Unsigned32,
				hwInfoPortPCIEBadTlp
					Unsigned32,
				hwInfoPortPCIEBalDllp
					Unsigned32,
				hwInfoPortPCIERecvError
					Unsigned32,
				hwInfoPortPCIEChipEccError
					Unsigned32,
				hwInfoPortPCIEStartTime
					OCTET STRING
			 }

		hwInfoPortPCIEID OBJECT-TYPE
			SYNTAX OCTET STRING
			MAX-ACCESS read-only
			STATUS current
			DESCRIPTION
				" "
			::= { hwInfoPortPCIEEntry 1 }

		
		hwInfoPortPCIELocation OBJECT-TYPE
			SYNTAX OCTET STRING
			MAX-ACCESS read-only
			STATUS current
			DESCRIPTION
				" "
			::= { hwInfoPortPCIEEntry 2 }

		
		hwInfoPortPCIEHealthStatus OBJECT-TYPE
			SYNTAX Unsigned32
			MAX-ACCESS read-only
			STATUS current
			DESCRIPTION
				" "
			::= { hwInfoPortPCIEEntry 3 }

		
		hwInfoPortPCIERunningStatus OBJECT-TYPE
			SYNTAX Unsigned32
			MAX-ACCESS read-only
			STATUS current
			DESCRIPTION
				" "
			::= { hwInfoPortPCIEEntry 4 }

		
		hwInfoPortPCIESpeed OBJECT-TYPE
			SYNTAX Unsigned32
			MAX-ACCESS read-only
			STATUS current
			DESCRIPTION
				" "
			::= { hwInfoPortPCIEEntry 5 }

		
		hwInfoPortPCIECurrentPeerPortID OBJECT-TYPE
			SYNTAX OCTET STRING
			MAX-ACCESS read-only
			STATUS current
			DESCRIPTION
				"  "
			::= { hwInfoPortPCIEEntry 6 }

		
		hwInfoPortPCIESuggestPeerPortID OBJECT-TYPE
			SYNTAX OCTET STRING
			MAX-ACCESS read-only
			STATUS current
			DESCRIPTION
				"  "
			::= { hwInfoPortPCIEEntry 7 }

		
		hwInfoPortPCIELostSignals OBJECT-TYPE
			SYNTAX Unsigned32
			MAX-ACCESS read-only
			STATUS current
			DESCRIPTION
				"  "
			::= { hwInfoPortPCIEEntry 8 }

		
		hwInfoPortPCIEECRCError OBJECT-TYPE
			SYNTAX Unsigned32
			MAX-ACCESS read-only
			STATUS current
			DESCRIPTION
				" "
			::= { hwInfoPortPCIEEntry 9 }

		
		hwInfoPortPCIEBadTlp OBJECT-TYPE
			SYNTAX Unsigned32
			MAX-ACCESS read-only
			STATUS current
			DESCRIPTION
				" "
			::= { hwInfoPortPCIEEntry 10 }

		
		hwInfoPortPCIEBalDllp OBJECT-TYPE
			SYNTAX Unsigned32
			MAX-ACCESS read-only
			STATUS current
			DESCRIPTION
				" "
			::= { hwInfoPortPCIEEntry 11 }

		
		hwInfoPortPCIERecvError OBJECT-TYPE
			SYNTAX Unsigned32
			MAX-ACCESS read-only
			STATUS current
			DESCRIPTION
				" "
			::= { hwInfoPortPCIEEntry 12 }

		
		hwInfoPortPCIEChipEccError OBJECT-TYPE
			SYNTAX Unsigned32
			MAX-ACCESS read-only
			STATUS current
			DESCRIPTION
				" "
			::= { hwInfoPortPCIEEntry 13 }

		
		hwInfoPortPCIEStartTime OBJECT-TYPE
			SYNTAX OCTET STRING
			MAX-ACCESS read-only
			STATUS current
			DESCRIPTION
				"  "
			::= { hwInfoPortPCIEEntry 14 }

		
		hwInfoPortSASTable OBJECT-TYPE
			SYNTAX SEQUENCE OF HwInfoPortSASEntry
			MAX-ACCESS not-accessible
			STATUS current
			DESCRIPTION
				" "
			::= { hwHardwareInfo 12 }

		
		hwInfoPortSASEntry OBJECT-TYPE
			SYNTAX HwInfoPortSASEntry
			MAX-ACCESS not-accessible
			STATUS current
			DESCRIPTION
				"  "
			INDEX { hwInfoPortSASID }
			::= { hwInfoPortSASTable 1 }

		
		HwInfoPortSASEntry ::=
			SEQUENCE { 
				hwInfoPortSASID
					OCTET STRING,
				hwInfoPortSASLocation
					OCTET STRING,
				hwInfoPortSASHealthStatus
					Unsigned32,
				hwInfoPortSASRunningStatus
					Unsigned32,
				hwInfoPortSASType
					Unsigned32,
				hwInfoPortSASWorkingRate
					Unsigned32,
				hwInfoPortSASWWN
					OCTET STRING,
				hwInfoPortSASRole
					Unsigned32,
				hwInfoPortSASInvalidDword
					Unsigned32,
				hwInfoPortSASConsistErrors
					Unsigned32,
				hwInfoPortSASLossOfDword
					Unsigned32,
				hwInfoPortSASPHYResetErrors
					Unsigned32,
				hwInfoPortSASStartTime
					OCTET STRING,
				hwInfoPortSASEnabled
					Unsigned32
			 }

		hwInfoPortSASID OBJECT-TYPE
			SYNTAX OCTET STRING
			MAX-ACCESS read-only
			STATUS current
			DESCRIPTION
				"  "
			::= { hwInfoPortSASEntry 1 }

		
		hwInfoPortSASLocation OBJECT-TYPE
			SYNTAX OCTET STRING
			MAX-ACCESS read-only
			STATUS current
			DESCRIPTION
				"  "
			::= { hwInfoPortSASEntry 2 }

		
		hwInfoPortSASHealthStatus OBJECT-TYPE
			SYNTAX Unsigned32
			MAX-ACCESS read-only
			STATUS current
			DESCRIPTION
				" "
			::= { hwInfoPortSASEntry 3 }

		
		hwInfoPortSASRunningStatus OBJECT-TYPE
			SYNTAX Unsigned32
			MAX-ACCESS read-only
			STATUS current
			DESCRIPTION
				"  "
			::= { hwInfoPortSASEntry 4 }

		
		hwInfoPortSASType OBJECT-TYPE
			SYNTAX Unsigned32
			MAX-ACCESS read-only
			STATUS current
			DESCRIPTION
				" "
			::= { hwInfoPortSASEntry 5 }

		
		hwInfoPortSASWorkingRate OBJECT-TYPE
			SYNTAX Unsigned32
			MAX-ACCESS read-only
			STATUS current
			DESCRIPTION
				"  "
			::= { hwInfoPortSASEntry 6 }

		
		hwInfoPortSASWWN OBJECT-TYPE
			SYNTAX OCTET STRING
			MAX-ACCESS read-only
			STATUS current
			DESCRIPTION
				"  "
			::= { hwInfoPortSASEntry 7 }

		
		hwInfoPortSASRole OBJECT-TYPE
			SYNTAX Unsigned32
			MAX-ACCESS read-only
			STATUS current
			DESCRIPTION
				"  "
			::= { hwInfoPortSASEntry 8 }

		
		hwInfoPortSASInvalidDword OBJECT-TYPE
			SYNTAX Unsigned32
			MAX-ACCESS read-only
			STATUS current
			DESCRIPTION
				" "
			::= { hwInfoPortSASEntry 9 }

		
		hwInfoPortSASConsistErrors OBJECT-TYPE
			SYNTAX Unsigned32
			MAX-ACCESS read-only
			STATUS current
			DESCRIPTION
				" "
			::= { hwInfoPortSASEntry 10 }

		
		hwInfoPortSASLossOfDword OBJECT-TYPE
			SYNTAX Unsigned32
			MAX-ACCESS read-only
			STATUS current
			DESCRIPTION
				"  "
			::= { hwInfoPortSASEntry 11 }

		
		hwInfoPortSASPHYResetErrors OBJECT-TYPE
			SYNTAX Unsigned32
			MAX-ACCESS read-only
			STATUS current
			DESCRIPTION
				"  "
			::= { hwInfoPortSASEntry 12 }

		
		hwInfoPortSASStartTime OBJECT-TYPE
			SYNTAX OCTET STRING
			MAX-ACCESS read-only
			STATUS current
			DESCRIPTION
				"  "
			::= { hwInfoPortSASEntry 13 }

		
		hwInfoPortSASEnabled OBJECT-TYPE
			SYNTAX Unsigned32
			MAX-ACCESS read-only
			STATUS current
			DESCRIPTION
				"  "
			::= { hwInfoPortSASEntry 14 }

		
		hwInfoInterfaceModuleTable OBJECT-TYPE
			SYNTAX SEQUENCE OF HwInfoInterfaceModuleEntry
			MAX-ACCESS not-accessible
			STATUS current
			DESCRIPTION
				" "
			::= { hwHardwareInfo 13 }

		
		hwInfoInterfaceModuleEntry OBJECT-TYPE
			SYNTAX HwInfoInterfaceModuleEntry
			MAX-ACCESS not-accessible
			STATUS current
			DESCRIPTION
				" "
			INDEX { hwInfoInterfaceModuleID }
			::= { hwInfoInterfaceModuleTable 1 }

		
		HwInfoInterfaceModuleEntry ::=
			SEQUENCE { 
				hwInfoInterfaceModuleID
					OCTET STRING,
				hwInfoInterfaceModuleLocation
					OCTET STRING,
				hwInfoInterfaceModuleHealthStatus
					Unsigned32,
				hwInfoInterfaceModuleRunningStatus
					Unsigned32,
				hwInfoInterfaceModuleModel
					Unsigned32,
				hwInfoInterfaceModuleLogicVersion
					OCTET STRING,
				hwInfoInterfaceModulePCBVersion
					OCTET STRING,
				hwInfoInterfaceModuleElectronicLabel
					OCTET STRING
			 }

		hwInfoInterfaceModuleID OBJECT-TYPE
			SYNTAX OCTET STRING
			MAX-ACCESS read-only
			STATUS current
			DESCRIPTION
				" "
			::= { hwInfoInterfaceModuleEntry 1 }

		
		hwInfoInterfaceModuleLocation OBJECT-TYPE
			SYNTAX OCTET STRING
			MAX-ACCESS read-only
			STATUS current
			DESCRIPTION
				" "
			::= { hwInfoInterfaceModuleEntry 2 }

		
		hwInfoInterfaceModuleHealthStatus OBJECT-TYPE
			SYNTAX Unsigned32
			MAX-ACCESS read-only
			STATUS current
			DESCRIPTION
				"  "
			::= { hwInfoInterfaceModuleEntry 3 }

		
		hwInfoInterfaceModuleRunningStatus OBJECT-TYPE
			SYNTAX Unsigned32
			MAX-ACCESS read-only
			STATUS current
			DESCRIPTION
				" "
			::= { hwInfoInterfaceModuleEntry 4 }

		
		hwInfoInterfaceModuleModel OBJECT-TYPE
			SYNTAX Unsigned32
			MAX-ACCESS read-only
			STATUS current
			DESCRIPTION
				"  "
			::= { hwInfoInterfaceModuleEntry 5 }

		
		hwInfoInterfaceModuleLogicVersion OBJECT-TYPE
			SYNTAX OCTET STRING
			MAX-ACCESS read-only
			STATUS current
			DESCRIPTION
				" "
			::= { hwInfoInterfaceModuleEntry 6 }

		
		hwInfoInterfaceModulePCBVersion OBJECT-TYPE
			SYNTAX OCTET STRING
			MAX-ACCESS read-only
			STATUS current
			DESCRIPTION
				" "
			::= { hwInfoInterfaceModuleEntry 7 }

		
		hwInfoInterfaceModuleElectronicLabel OBJECT-TYPE
			SYNTAX OCTET STRING
			MAX-ACCESS read-only
			STATUS current
			DESCRIPTION
				" "
			::= { hwInfoInterfaceModuleEntry 8 }

		
		hwInfoExpBoardTable OBJECT-TYPE
			SYNTAX SEQUENCE OF HwInfoExpBoardEntry
			MAX-ACCESS not-accessible
			STATUS current
			DESCRIPTION
				" "
			::= { hwHardwareInfo 14 }

		
		hwInfoExpBoardEntry OBJECT-TYPE
			SYNTAX HwInfoExpBoardEntry
			MAX-ACCESS not-accessible
			STATUS current
			DESCRIPTION
				" "
			INDEX { hwInfoExpBoardID }
			::= { hwInfoExpBoardTable 1 }

		
		HwInfoExpBoardEntry ::=
			SEQUENCE { 
				hwInfoExpBoardID
					OCTET STRING,
				hwInfoExpBoardLocation
					OCTET STRING,
				hwInfoExpBoardHealthStatus
					Unsigned32,
				hwInfoExpBoardRunningStatus
					Unsigned32,
				hwInfoExpBoardModel
					Unsigned32,
				hwInfoExpBoardLogicVersion
					OCTET STRING,
				hwInfoExpBoardPCBVersion
					OCTET STRING,
				hwInfoExpBoardSESVersion
					OCTET STRING,
				hwInfoExpBoardELabel
					OCTET STRING
			 }

		hwInfoExpBoardID OBJECT-TYPE
			SYNTAX OCTET STRING
			MAX-ACCESS read-only
			STATUS current
			DESCRIPTION
				"  "
			::= { hwInfoExpBoardEntry 1 }

		
		hwInfoExpBoardLocation OBJECT-TYPE
			SYNTAX OCTET STRING
			MAX-ACCESS read-only
			STATUS current
			DESCRIPTION
				"  "
			::= { hwInfoExpBoardEntry 2 }

		
		hwInfoExpBoardHealthStatus OBJECT-TYPE
			SYNTAX Unsigned32
			MAX-ACCESS read-only
			STATUS current
			DESCRIPTION
				"  "
			::= { hwInfoExpBoardEntry 3 }

		
		hwInfoExpBoardRunningStatus OBJECT-TYPE
			SYNTAX Unsigned32
			MAX-ACCESS read-only
			STATUS current
			DESCRIPTION
				"  "
			::= { hwInfoExpBoardEntry 4 }

		
		hwInfoExpBoardModel OBJECT-TYPE
			SYNTAX Unsigned32
			MAX-ACCESS read-only
			STATUS current
			DESCRIPTION
				"  "
			::= { hwInfoExpBoardEntry 5 }

		
		hwInfoExpBoardLogicVersion OBJECT-TYPE
			SYNTAX OCTET STRING
			MAX-ACCESS read-only
			STATUS current
			DESCRIPTION
				"  "
			::= { hwInfoExpBoardEntry 6 }

		
		hwInfoExpBoardPCBVersion OBJECT-TYPE
			SYNTAX OCTET STRING
			MAX-ACCESS read-only
			STATUS current
			DESCRIPTION
				"  "
			::= { hwInfoExpBoardEntry 7 }

		
		hwInfoExpBoardSESVersion OBJECT-TYPE
			SYNTAX OCTET STRING
			MAX-ACCESS read-only
			STATUS current
			DESCRIPTION
				"  "
			::= { hwInfoExpBoardEntry 8 }

		
		hwInfoExpBoardELabel OBJECT-TYPE
			SYNTAX OCTET STRING
			MAX-ACCESS read-only
			STATUS current
			DESCRIPTION
				"  "
			::= { hwInfoExpBoardEntry 9 }

		

		hwInfoRapidDiskTable OBJECT-TYPE
			SYNTAX SEQUENCE OF HwInfoRapidDiskEntry
			MAX-ACCESS not-accessible
			STATUS current
			DESCRIPTION
				" "
			::= { hwHardwareInfo 15 }

		

		hwInfoRapidDiskEntry OBJECT-TYPE
			SYNTAX HwInfoRapidDiskEntry
			MAX-ACCESS not-accessible
			STATUS current
			DESCRIPTION
				" "
			INDEX { hwInfoRapidDiskID }
			::= { hwInfoRapidDiskTable 1 }

		
		HwInfoRapidDiskEntry ::=
			SEQUENCE { 
				hwInfoRapidDiskID
					OCTET STRING,
				hwInfoRapidDiskHealthStatus
					Unsigned32,
				hwInfoRapidDiskRunningStatus
					Unsigned32,
				hwInfoRapidDiskLocation
					OCTET STRING,
				hwInfoRapidDiskType
					Unsigned32,
				hwInfoRapidDiskCapacity
					Counter64,
				hwInfoRapidDiskRole
					Unsigned32,
				hwInfoRapidDiskSpeed
					Unsigned32,
				hwInfoRapidDiskInterfaceBandwidth
					Unsigned32,
				hwInfoRapidDiskSectorSize
					Unsigned32,
				hwInfoRapidDiskModel
					OCTET STRING,
				hwInfoRapidDiskFirmwareVersion
					OCTET STRING,
				hwInfoRapidDiskManufacturer
					OCTET STRING,
				hwInfoRapidDiskSerialNumber
					OCTET STRING,
				hwInfoRapidDiskDiskDomainID
					OCTET STRING,
				hwInfoRapidDiskDiskDomainName
					OCTET STRING,
				hwInfoRapidDiskDiskDomainTierID
					OCTET STRING,
				hwInfoRapidDiskCofferDisk
					Unsigned32,
				hwInfoRapidDiskProgress
					Unsigned32,
				hwInfoRapidDiskBarCode
					OCTET STRING,
				hwInfoRapidDiskCapacityUsage
					Unsigned32,
				hwInfoRapidDiskHealthMark
					Unsigned32
			 }


		hwInfoRapidDiskID OBJECT-TYPE
			SYNTAX OCTET STRING
			MAX-ACCESS read-only
			STATUS current
			DESCRIPTION
				"  "
			::= { hwInfoRapidDiskEntry 1 }


		hwInfoRapidDiskHealthStatus OBJECT-TYPE
			SYNTAX Unsigned32
			MAX-ACCESS read-only
			STATUS current
			DESCRIPTION
				"  "
			::= { hwInfoRapidDiskEntry 2 }
		

		hwInfoRapidDiskRunningStatus OBJECT-TYPE
			SYNTAX Unsigned32
			MAX-ACCESS read-only
			STATUS current
			DESCRIPTION
				"  "
			::= { hwInfoRapidDiskEntry 3 }
		

		hwInfoRapidDiskLocation OBJECT-TYPE
			SYNTAX OCTET STRING
			MAX-ACCESS read-only
			STATUS current
			DESCRIPTION
				"  "
			::= { hwInfoRapidDiskEntry 4 }

		

		hwInfoRapidDiskType OBJECT-TYPE
			SYNTAX Unsigned32
			MAX-ACCESS read-only
			STATUS current
			DESCRIPTION
				"  "
			::= { hwInfoRapidDiskEntry 5 }

		


		hwInfoRapidDiskCapacity OBJECT-TYPE
			SYNTAX Counter64
			MAX-ACCESS read-only
			STATUS current
			DESCRIPTION
				"  "
			::= { hwInfoRapidDiskEntry 6 }

		

		hwInfoRapidDiskRole OBJECT-TYPE
			SYNTAX Unsigned32
			MAX-ACCESS read-only
			STATUS current
			DESCRIPTION
				" "
			::= { hwInfoRapidDiskEntry 7 }

		

		hwInfoRapidDiskSpeed OBJECT-TYPE
			SYNTAX Unsigned32
			MAX-ACCESS read-only
			STATUS current
			DESCRIPTION
				"  "
			::= { hwInfoRapidDiskEntry 8 }

		

		hwInfoRapidDiskInterfaceBandwidth OBJECT-TYPE
			SYNTAX Unsigned32
			MAX-ACCESS read-only
			STATUS current
			DESCRIPTION
				"  "
			::= { hwInfoRapidDiskEntry 9 }

		

		hwInfoRapidDiskSectorSize OBJECT-TYPE
			SYNTAX Unsigned32
			MAX-ACCESS read-only
			STATUS current
			DESCRIPTION
				"  "
			::= { hwInfoRapidDiskEntry 10 }

		

		hwInfoRapidDiskModel OBJECT-TYPE
			SYNTAX OCTET STRING
			MAX-ACCESS read-only
			STATUS current
			DESCRIPTION
				"  "
			::= { hwInfoRapidDiskEntry 11 }

		

		hwInfoRapidDiskFirmwareVersion OBJECT-TYPE
			SYNTAX OCTET STRING
			MAX-ACCESS read-only
			STATUS current
			DESCRIPTION
				"  "
			::= { hwInfoRapidDiskEntry 12 }

		

		hwInfoRapidDiskManufacturer OBJECT-TYPE
			SYNTAX OCTET STRING
			MAX-ACCESS read-only
			STATUS current
			DESCRIPTION
				"  "
			::= { hwInfoRapidDiskEntry 13 }



		hwInfoRapidDiskSerialNumber OBJECT-TYPE
			SYNTAX OCTET STRING
			MAX-ACCESS read-only
			STATUS current
			DESCRIPTION
				"  "
			::= { hwInfoRapidDiskEntry 14 }

		

		hwInfoRapidDiskDiskDomainID OBJECT-TYPE
			SYNTAX OCTET STRING
			MAX-ACCESS read-only
			STATUS current
			DESCRIPTION
				" "
			::= { hwInfoRapidDiskEntry 15 }

		

		hwInfoRapidDiskDiskDomainName OBJECT-TYPE
			SYNTAX OCTET STRING
			MAX-ACCESS read-only
			STATUS current
			DESCRIPTION
				"  "
			::= { hwInfoRapidDiskEntry 16 }

		

		hwInfoRapidDiskDiskDomainTierID OBJECT-TYPE
			SYNTAX OCTET STRING
			MAX-ACCESS read-only
			STATUS current
			DESCRIPTION
				"  "
			::= { hwInfoRapidDiskEntry 17 }

		

		hwInfoRapidDiskCofferDisk OBJECT-TYPE
			SYNTAX Unsigned32
			MAX-ACCESS read-only
			STATUS current
			DESCRIPTION
				"  "
			::= { hwInfoRapidDiskEntry 18 }

		

		hwInfoRapidDiskProgress OBJECT-TYPE
			SYNTAX Unsigned32
			MAX-ACCESS read-only
			STATUS current
			DESCRIPTION
				"  "
			::= { hwInfoRapidDiskEntry 19 }

		

		hwInfoRapidDiskBarCode OBJECT-TYPE
			SYNTAX OCTET STRING
			MAX-ACCESS read-only
			STATUS current
			DESCRIPTION
				"  "
			::= { hwInfoRapidDiskEntry 20 }

		

		hwInfoRapidDiskCapacityUsage OBJECT-TYPE
			SYNTAX Unsigned32
			MAX-ACCESS read-only
			STATUS current
			DESCRIPTION
				"  "
			::= { hwInfoRapidDiskEntry 21 }

		

		hwInfoRapidDiskHealthMark OBJECT-TYPE
			SYNTAX Unsigned32
			MAX-ACCESS read-only
			STATUS current
			DESCRIPTION
				"  "
			::= { hwInfoRapidDiskEntry 22 }
		

		isoConformance OBJECT IDENTIFIER ::= { iso 6 }

		
		isoGroups OBJECT IDENTIFIER ::= { isoConformance 1 }

		
		currentObjectGroup OBJECT-GROUP
			OBJECTS { hwInfoPortComID, hwInfoPortComLocation, hwInfoPortComHealthStatus, hwInfoPortComRunningStatus, hwInfoPortComType, 
				hwInfoPortEthID, hwInfoPortEthLocation, hwInfoPortEthHealthStatus, hwInfoPortEthRunningStatus, hwInfoPortEthType, 
				hwInfoPortEthIPv4Address, hwInfoPortEthSubnetMask, hwInfoPortEthIPv4Gateway, hwInfoPortEthIPv6Address, hwInfoPortEthIPv6PrefixLength, 
				hwInfoPortEthIPv6Gateway, hwInfoPortEthMAC, hwInfoPortEthRole, hwInfoPortEthMode, hwInfoPortEthMTU, 
				hwInfoPortEthWorkingRate, hwInfoPortEthBondName, hwInfoPortEthiSCSIPort, hwInfoPortEthiSCSIName, hwInfoPortEthErrorPackets, 
				hwInfoPortEthLostPackages, hwInfoPortFCID, hwInfoPortFCLocation, hwInfoPortFCHealthStatus, hwInfoPortFCRunningStatus, 
				hwInfoPortFCType, hwInfoPortFCWorkingRate, hwInfoPortFCConfiguredSpeed, hwInfoPortFCWWN, hwInfoPortFCRole, 
				hwInfoPortFCSFPStatus, hwInfoPortFCWorkingMode, hwInfoPortFCConfiguredMode, hwInfoPortFCFloginDelayTimes, hwInfoPortFCLostSignals, 
				hwInfoPortFCLinkErrorsCodes, hwInfoPortFCLostSynchronizations, hwInfoPortFCFailedConnections, hwInfoPortFCoEID, hwInfoPortFCoELocation, 
				hwInfoPortFCoEHealthStatus, hwInfoPortFCoERunningStatus, hwInfoPortFCoEType, hwInfoPortFCoEWorkingRate, hwInfoPortFCoEWWN, 
				hwInfoPortFCoERole, hwInfoPortFCoESFPStatus, hwInfoPortFCoEErrorPackets, hwInfoPortFCoELostPackets, hwInfoPortFCoEOverFlowedPackets, 
				hwInfoPortFCoEStartTime, hwInfoPortPCIEID, hwInfoPortPCIELocation, hwInfoPortPCIEHealthStatus, hwInfoPortPCIERunningStatus, 
				hwInfoPortPCIESpeed, hwInfoPortPCIECurrentPeerPortID, hwInfoPortPCIESuggestPeerPortID, hwInfoPortPCIELostSignals, hwInfoPortPCIEECRCError, 
				hwInfoPortPCIEBadTlp, hwInfoPortPCIEBalDllp, hwInfoPortPCIERecvError, hwInfoPortPCIEChipEccError, hwInfoPortSASID, 
				hwInfoPortSASLocation, hwInfoPortSASHealthStatus, hwInfoPortSASRunningStatus, hwInfoPortSASType, hwInfoPortSASWorkingRate, 
				hwInfoPortSASWWN, hwInfoPortSASRole, hwInfoPortSASInvalidDword, hwInfoPortSASConsistErrors, hwInfoPortSASLossOfDword, 
				hwInfoPortSASPHYResetErrors, hwInfoPortSASStartTime, hwInfoPortSASEnabled, hwInfoInterfaceModuleID, hwInfoInterfaceModuleLocation, 
				hwInfoInterfaceModuleHealthStatus, hwInfoInterfaceModuleRunningStatus, hwInfoInterfaceModuleModel, hwInfoInterfaceModuleLogicVersion, hwInfoInterfaceModulePCBVersion, 
				hwInfoInterfaceModuleElectronicLabel, hwInfoDiskID, hwInfoDiskHealthStatus, hwInfoDiskRunningStatus, hwInfoDiskType, 
				hwInfoDiskCapacity, hwInfoDiskRole, hwInfoDiskSpeed, hwInfoDiskInterfaceBandwidth, hwInfoDiskSectorSize, 
				hwInfoDiskTemperature, hwInfoDiskModel, hwInfoDiskFirmwareVersion, hwInfoDiskManufacturer, hwInfoDiskSerialNumber, 
				hwInfoDiskLightStatus, hwInfoDiskDiskDomainID, hwInfoDiskDiskDomainName, hwInfoDiskDiskDomainTierID, hwInfoDiskCofferDisk, 
				hwInfoDiskRunTime, hwInfoDiskProgress, hwInfoDiskBarCode, hwInfoDiskCapacityUsage, hwInfoDiskHealthMark, 
				hwInfoControllerHealthStatus, hwInfoControllerRunningStatus, hwInfoControllerCPU, hwInfoControllerRole, hwInfoControllerCacheCapacity, 
				hwInfoControllerCPUUsage, hwInfoControllerMemoryUsage, hwInfoControllerVoltage, hwInfoControllerSoftwareVersion, hwInfoControllerPCBVersion, 
				hwInfoControllerSESVersion, hwInfoControllerBMCVersion, hwInfoControllerLogicVersion, hwInfoControllerBIOSVersion, hwInfoControllerElectronicLabel, 
				hwInfoPowerHealthStatus, hwInfoPowerRunningStatus, hwInfoPowerManufacturer, hwInfoPowerProduceDate, hwInfoPowerSerialNumber, 
				hwInfoFanHealthStatus, hwInfoFanElectronicLabel, hwInfoBBUHealthStatus, hwInfoBBURunningStatus, hwInfoBBUType, 
				hwInfoBBUNumberOfDischarges, hwInfoBBUFirmwareVersion, hwInfoBBUDeliveredOn, hwInfoBBUOwningController, hwInfoBBUElectronicLabel, 
				hwInfoEnclosureID, hwInfoEnclosureLogicType, hwInfoEnclosureHealthStatus, hwInfoEnclosureRunningStatus, hwInfoEnclosureLocation, 
				hwInfoEnclosureType, hwInfoEnclosureTemperature, hwInfoEnclosureSN, hwInfoEnclosureMAC, hwInfoEnclosureHeight, 
				hwInfoEnclosureExpansionDepth, hwInfoFanRunningStatus, hwInfoFanRunningLevel, hwInfoPowerModle, hwInfoPowerVersion, 
				hwInfoControllerID, hwInfoPowerID, hwInfoPowerType, hwInfoBBUID, hwInfoControllerLocation, 
				hwInfoDiskLocation, hwInfoEnclosureName, hwInfoEnclosureElectronicLabel, hwInfoPowerLocation, hwInfoFanLocation, 
				hwInfoBBULocation, hwInfoPortFCStartTime, hwInfoPortEthStartTime, hwInfoPortPCIEStartTime, hwInfoExpBoardID, 
				hwInfoExpBoardLocation, hwInfoExpBoardHealthStatus, hwInfoExpBoardRunningStatus, hwInfoExpBoardModel, hwInfoExpBoardLogicVersion, 
				hwInfoExpBoardPCBVersion, hwInfoExpBoardSESVersion, hwInfoExpBoardELabel, hwInfoRapidDiskLocation, hwInfoRapidDiskHealthStatus, 
				hwInfoRapidDiskRunningStatus, hwInfoRapidDiskID, hwInfoBBUCurrentVoltage, hwInfoFanID, hwInfoRapidDiskType, 
				hwInfoRapidDiskRole, hwInfoRapidDiskCapacity, hwInfoRapidDiskInterfaceBandwidth, hwInfoRapidDiskSpeed, hwInfoRapidDiskModel, 
				hwInfoRapidDiskSectorSize, hwInfoRapidDiskManufacturer, hwInfoRapidDiskFirmwareVersion, hwInfoRapidDiskDiskDomainID, hwInfoRapidDiskSerialNumber, 
				hwInfoRapidDiskDiskDomainTierID, hwInfoRapidDiskCofferDisk, hwInfoRapidDiskDiskDomainName, hwInfoRapidDiskProgress, hwInfoRapidDiskBarCode, 
				hwInfoRapidDiskCapacityUsage, hwInfoRapidDiskHealthMark }
			STATUS current
			DESCRIPTION 
				"Enter the description of the created OBJECT-GROUP."
			::= { isoGroups 1 }

		
		isoCompliances OBJECT IDENTIFIER ::= { isoConformance 2 }

		
--  this module
		basicCompliance MODULE-COMPLIANCE
			STATUS current
			DESCRIPTION 
				"Enter the description of the created MODULE-COMPLIANCE."
			MODULE -- this module
				MANDATORY-GROUPS { currentObjectGroup }
			::= { isoCompliances 1 }

		
	
	END

--
-- HUAWEI-STORAGE-HARDWARE-MIB.mib
--
