--
-- ISM-PERFORMANCE-MIB.mib
-- MIB generated by MG-SOFT Visual MIB Builder Version 3.0 Build 253
-- Saturday, November 28, 2015 at 17:02:21
--

--  ISM-PERFORMANCE-MIB.mib
-- MIB generated by MG-SOFT Visual MIB Builder Version 3.0 Build 253
-- Monday, November 16, 2015 at 11:40:36
-- 
--  ISM-PERFORMANCE-MIB.mib
-- MIB generated by MG-SOFT Visual MIB Builder Version 4.0 Build 347
-- Thursday, March 27, 2014 at 11:42:32
-- 

	ISM-PERFORMANCE-MIB DEFINITIONS ::= BEGIN
 
                IMPORTS
                        OBJECT-GROUP, MODULE-COMPLIANCE
                                FROM SNMPv2-CONF
                        Integer32, Unsigned32, OBJECT-TYPE, MODULE-IDENTITY, enterprises
                                FROM SNMPv2-SMI
                        DisplayString, DateAndTime, RowStatus, TEXTUAL-CONVENTION
                                FROM SNMPv2-TC;

	
		hwStorage MODULE-IDENTITY 
			LAST-UPDATED "201507252025Z"		-- July 25, 2015 at 20:25 GMT
			ORGANIZATION 
				"Huawei Technologies Co.,Ltd."
			CONTACT-INFO 
				"Huawei Industrial Base
				Bantian, Longgang
				Shenzhen 518129
				People's Republic of China
				Website: http://www.huawei.com
				Email: support@huawei.com"
			DESCRIPTION 
				"Description."
			REVISION "201304071716Z"		-- April 07, 2013 at 17:16 GMT
			DESCRIPTION
				"Description."
			::= { huaweistorage 4 }
		
	
--
-- Textual conventions
--
	
--  August 11, 2010 at 12:39 GMT
-- April 07, 2013 at 17:16 GMT
-- 
-- Textual conventions
-- 
--  August 11, 2010 at 12:39 GMT
-- April 07, 2013 at 17:16 GMT
-- 
-- Textual conventions
-- 
		NodeCodeString ::= TEXTUAL-CONVENTION
			DISPLAY-HINT 
				"255a"
			STATUS current
			DESCRIPTION 
				"characters in length."
			SYNTAX OCTET STRING (SIZE (15..17))
			
--
-- Node definitions
--

--  RowStatus ::= INTEGER
-- {
-- active(1),
-- notInService(2),
-- notReady(3),
-- createAndGo(4),
-- createAndWait(5),
-- destroy(6)
-- }
--
-- Node definitions
--
-- Node definitions
--
-- Node definitions
--
-- Node definitions
--
-- 1
-- 1
-- 1
-- 1
-- iso OBJECT IDENTIFIER ::= {  1 }
--   1.3
-- 1.3
-- 1.3
-- 1.3
-- 1.3
-- org OBJECT IDENTIFIER ::= { iso 3 }
--   1.3.6
-- 1.3.6
-- 1.3.6
-- 1.3.6
-- 1.3.6
-- dod OBJECT IDENTIFIER ::= { org 6 }
--   1.3.6.1
-- 1.3.6.1
-- 1.3.6.1
-- 1.3.6.1
-- 1.3.6.1
-- internet OBJECT IDENTIFIER ::= { dod 1 }
--   1.3.6.1.4
-- 1.3.6.1.4
-- 1.3.6.1.4
-- 1.3.6.1.4
-- 1.3.6.1.4
-- private OBJECT IDENTIFIER ::= { internet 4 }
--   1.3.6.1.4.1
-- 1.3.6.1.4.1
-- 1.3.6.1.4.1
-- 1.3.6.1.4.1
-- 1.3.6.1.4.1
-- enterprise OBJECT IDENTIFIER ::= { private 1 }
--  1.3.6.1.4.1.34774
-- 1.3.6.1.4.1.34774
-- 1.3.6.1.4.1.34774
-- 1.3.6.1.4.1.34774
-- 1.3.6.1.4.1.34774	
		huaweistorage OBJECT IDENTIFIER ::= { enterprises 34774 }
		
--  1.3.6.1.4.1.34774.4.1
		-- 1.3.6.1.4.1.34774.4.1
		hwISM OBJECT IDENTIFIER ::= { hwStorage 1 }
		
--  1.3.6.1.4.1.34774.4.1.21
		-- 1.3.6.1.4.1.34774.4.1.21
		hwPerformance OBJECT IDENTIFIER ::= { hwISM 21 }
		
--  1.3.6.1.4.1.34774.4.1.21.1
		-- 1.3.6.1.4.1.34774.4.1.21.1
		hwPerformanceSwitch OBJECT-TYPE
			SYNTAX Integer32 (0..1)
			MAX-ACCESS read-write
			STATUS current
			DESCRIPTION
				"device performance switch.
				on/off - 1/0"
			::= { hwPerformance 1 }
		
--  1.3.6.1.4.1.34774.4.1.21.3
		-- 1.3.6.1.4.1.34774.4.1.21.3
		hwPerfNodeTable OBJECT-TYPE
			SYNTAX SEQUENCE OF HwPerfNodeEntry
			MAX-ACCESS not-accessible
			STATUS current
			DESCRIPTION
				" "
			::= { hwPerformance 3 }
		
--  1.3.6.1.4.1.34774.4.1.21.3.1
		-- 1.3.6.1.4.1.34774.4.1.21.3.1
		hwPerfNodeEntry OBJECT-TYPE
			SYNTAX HwPerfNodeEntry
			MAX-ACCESS not-accessible
			STATUS current
			DESCRIPTION
				"performance object info table"
			INDEX { hwPerfNodeIfIndex }
			::= { hwPerfNodeTable 1 }
		
		HwPerfNodeEntry ::=
			SEQUENCE { 
				hwPerfNodeIfIndex
					Unsigned32,
				hwPerfNodeCPUUsage
					Unsigned32,
				hwPerfNodeMemoryUsage
					Unsigned32,
				hwPerfNodeDelay
					Unsigned32,
				hwPerfNodeTotalIOPS
					Unsigned32,
				hwPerfNodeReadIOPS
					Unsigned32,
				hwPerfNodeWriteIOPS
					Unsigned32,
				hwPerfNodeTotalTraffic
					Unsigned32,
				hwPerfNodeReadTraffic
					Unsigned32,
				hwPerfNodeWriteTraffic
					Unsigned32,
				hwPerfNodeAverageIOResponseTime
					Unsigned32,
				hwPerfNodeMaxIOResponseTime
					Unsigned32,
				hwPerfNodeAverageReadIOLatency
					Unsigned32,
				hwPerfNodeAverageWriteIOLatency
					Unsigned32
			 }

--  1.3.6.1.4.1.34774.4.1.21.3.1.1
		-- 1.3.6.1.4.1.34774.4.1.21.3.1.1
		hwPerfNodeIfIndex OBJECT-TYPE
			SYNTAX Unsigned32
			MAX-ACCESS read-only
			STATUS current
			DESCRIPTION
				" "
			::= { hwPerfNodeEntry 1 }
		
--  1.3.6.1.4.1.34774.4.1.21.3.1.2
		-- 1.3.6.1.4.1.34774.4.1.21.3.1.2
		hwPerfNodeCPUUsage OBJECT-TYPE
			SYNTAX Unsigned32
			MAX-ACCESS read-only
			STATUS current
			DESCRIPTION
				" "
			::= { hwPerfNodeEntry 2 }
		
--  1.3.6.1.4.1.34774.4.1.21.3.1.3
		-- 1.3.6.1.4.1.34774.4.1.21.3.1.3
		hwPerfNodeMemoryUsage OBJECT-TYPE
			SYNTAX Unsigned32
			MAX-ACCESS read-only
			STATUS current
			DESCRIPTION
				"Description."
			::= { hwPerfNodeEntry 3 }
		
--  1.3.6.1.4.1.34774.4.1.21.3.1.4
		-- 1.3.6.1.4.1.34774.4.1.21.3.1.4
		hwPerfNodeDelay OBJECT-TYPE
			SYNTAX Unsigned32
			MAX-ACCESS read-only
			STATUS current
			DESCRIPTION
				"Description."
			::= { hwPerfNodeEntry 4 }
		
--  1.3.6.1.4.1.34774.4.1.21.3.1.5
		-- 1.3.6.1.4.1.34774.4.1.21.3.1.5
		hwPerfNodeTotalIOPS OBJECT-TYPE
			SYNTAX Unsigned32
			MAX-ACCESS read-only
			STATUS current
			DESCRIPTION
				" "
			::= { hwPerfNodeEntry 5 }
		
--  1.3.6.1.4.1.34774.4.1.21.3.1.6
		-- 1.3.6.1.4.1.34774.4.1.21.3.1.6
		hwPerfNodeReadIOPS OBJECT-TYPE
			SYNTAX Unsigned32
			MAX-ACCESS read-only
			STATUS current
			DESCRIPTION
				" "
			::= { hwPerfNodeEntry 6 }
		
--  1.3.6.1.4.1.34774.4.1.21.3.1.7
		-- 1.3.6.1.4.1.34774.4.1.21.3.1.7
		hwPerfNodeWriteIOPS OBJECT-TYPE
			SYNTAX Unsigned32
			MAX-ACCESS read-only
			STATUS current
			DESCRIPTION
				" "
			::= { hwPerfNodeEntry 7 }
		
--  1.3.6.1.4.1.34774.4.1.21.3.1.8
		-- 1.3.6.1.4.1.34774.4.1.21.3.1.8
		hwPerfNodeTotalTraffic OBJECT-TYPE
			SYNTAX Unsigned32
			MAX-ACCESS read-only
			STATUS current
			DESCRIPTION
				"Description."
			::= { hwPerfNodeEntry 8 }
		
--  1.3.6.1.4.1.34774.4.1.21.3.1.9
		-- 1.3.6.1.4.1.34774.4.1.21.3.1.9
		hwPerfNodeReadTraffic OBJECT-TYPE
			SYNTAX Unsigned32
			MAX-ACCESS read-only
			STATUS current
			DESCRIPTION
				"Description."
			::= { hwPerfNodeEntry 9 }
		
--  1.3.6.1.4.1.34774.4.1.21.3.1.10
		-- 1.3.6.1.4.1.34774.4.1.21.3.1.10
		hwPerfNodeWriteTraffic OBJECT-TYPE
			SYNTAX Unsigned32
			MAX-ACCESS read-only
			STATUS current
			DESCRIPTION
				"Description."
			::= { hwPerfNodeEntry 10 }
		
--  1.3.6.1.4.1.34774.4.1.21.3.1.13
		-- 1.3.6.1.4.1.34774.4.1.21.3.1.13
		hwPerfNodeAverageIOResponseTime OBJECT-TYPE
			SYNTAX Unsigned32
			MAX-ACCESS read-only
			STATUS current
			DESCRIPTION
				"Description."
			::= { hwPerfNodeEntry 13 }
		
--  1.3.6.1.4.1.34774.4.1.21.3.1.14
		-- 1.3.6.1.4.1.34774.4.1.21.3.1.14
		hwPerfNodeMaxIOResponseTime OBJECT-TYPE
			SYNTAX Unsigned32
			MAX-ACCESS read-only
			STATUS current
			DESCRIPTION
				"Description."
			::= { hwPerfNodeEntry 14 }
		
--  1.3.6.1.4.1.34774.4.1.21.3.1.17
		-- 1.3.6.1.4.1.34774.4.1.21.3.1.15
		hwPerfNodeAverageReadIOLatency OBJECT-TYPE
			SYNTAX Unsigned32
			MAX-ACCESS read-only
			STATUS current
			DESCRIPTION
				"Description."
			::= { hwPerfNodeEntry 15 }
		
--  1.3.6.1.4.1.34774.4.1.21.3.1.18
		-- 1.3.6.1.4.1.34774.4.1.21.3.1.16
		hwPerfNodeAverageWriteIOLatency OBJECT-TYPE
			SYNTAX Unsigned32
			MAX-ACCESS read-only
			STATUS current
			DESCRIPTION
				"Description."
			::= { hwPerfNodeEntry 16 }
		
--  1.3.6.1.4.1.34774.4.1.21.4
		-- 1.3.6.1.4.1.34774.4.1.21.4
		hwPerfLunTable OBJECT-TYPE
			SYNTAX SEQUENCE OF HwPerfLunEntry
			MAX-ACCESS not-accessible
			STATUS current
			DESCRIPTION
				" "
			::= { hwPerformance 4 }
		
--  1.3.6.1.4.1.34774.4.1.21.4.1
		-- 1.3.6.1.4.1.34774.4.1.21.4.1
		hwPerfLunEntry OBJECT-TYPE
			SYNTAX HwPerfLunEntry
			MAX-ACCESS not-accessible
			STATUS current
			DESCRIPTION
				"Description."
			INDEX { hwPerfLunID }
			::= { hwPerfLunTable 1 }
		
		HwPerfLunEntry ::=
			SEQUENCE { 
				hwPerfLunID
					Unsigned32,
				hwPerfLunHitRate
					Unsigned32,
				hwPerfLunTotalIOPS
					Unsigned32,
				hwPerfLunReadIOPS
					Unsigned32,
				hwPerfLunWriteIOPS
					Unsigned32,
				hwPerfLunTotalTraffic
					Unsigned32,
				hwPerfLunReadTraffic
					Unsigned32,
				hwPerfLunWriteTraffic
					Unsigned32,
				hwPerfLunReadIORate
					Unsigned32,
				hwPerfLunWriteIORate
					Unsigned32,
				hwPerfLunMaxTraffic
					Unsigned32,
				hwPerfLunMaxIOPS
					Unsigned32,
				hwPerfLunAverageIOResponseTime
					Unsigned32,
				hwPerfLunMaxIOResponseTime
					Unsigned32,
				hwPerfLunAverageReadIOLatency
					Unsigned32,
				hwPerfLunAverageWriteIOLatency
					Unsigned32
			 }

--  1.3.6.1.4.1.34774.4.1.21.4.1.1
		-- 1.3.6.1.4.1.34774.4.1.21.4.1.1
		hwPerfLunID OBJECT-TYPE
			SYNTAX Unsigned32
			MAX-ACCESS read-only
			STATUS current
			DESCRIPTION
				" "
			::= { hwPerfLunEntry 1 }
		
--  1.3.6.1.4.1.34774.4.1.21.4.1.2
		-- 1.3.6.1.4.1.34774.4.1.21.4.1.2
		hwPerfLunHitRate OBJECT-TYPE
			SYNTAX Unsigned32
			MAX-ACCESS read-only
			STATUS current
			DESCRIPTION
				" "
			::= { hwPerfLunEntry 2 }
		
--  1.3.6.1.4.1.34774.4.1.21.4.1.3
		-- 1.3.6.1.4.1.34774.4.1.21.4.1.3
		hwPerfLunTotalIOPS OBJECT-TYPE
			SYNTAX Unsigned32
			MAX-ACCESS read-only
			STATUS current
			DESCRIPTION
				" "
			::= { hwPerfLunEntry 3 }
		
--  1.3.6.1.4.1.34774.4.1.21.4.1.4
		-- 1.3.6.1.4.1.34774.4.1.21.4.1.4
		hwPerfLunReadIOPS OBJECT-TYPE
			SYNTAX Unsigned32
			MAX-ACCESS read-only
			STATUS current
			DESCRIPTION
				" "
			::= { hwPerfLunEntry 4 }
		
--  1.3.6.1.4.1.34774.4.1.21.4.1.5
		-- 1.3.6.1.4.1.34774.4.1.21.4.1.5
		hwPerfLunWriteIOPS OBJECT-TYPE
			SYNTAX Unsigned32
			MAX-ACCESS read-only
			STATUS current
			DESCRIPTION
				" "
			::= { hwPerfLunEntry 5 }
		
--  1.3.6.1.4.1.34774.4.1.21.4.1.6
		-- 1.3.6.1.4.1.34774.4.1.21.4.1.6
		hwPerfLunTotalTraffic OBJECT-TYPE
			SYNTAX Unsigned32
			MAX-ACCESS read-only
			STATUS current
			DESCRIPTION
				"Description."
			::= { hwPerfLunEntry 6 }
		
--  1.3.6.1.4.1.34774.4.1.21.4.1.7
		-- 1.3.6.1.4.1.34774.4.1.21.4.1.7
		hwPerfLunReadTraffic OBJECT-TYPE
			SYNTAX Unsigned32
			MAX-ACCESS read-only
			STATUS current
			DESCRIPTION
				"Description."
			::= { hwPerfLunEntry 7 }
		
--  1.3.6.1.4.1.34774.4.1.21.4.1.8
		-- 1.3.6.1.4.1.34774.4.1.21.4.1.8
		hwPerfLunWriteTraffic OBJECT-TYPE
			SYNTAX Unsigned32
			MAX-ACCESS read-only
			STATUS current
			DESCRIPTION
				"Description."
			::= { hwPerfLunEntry 8 }
		
--  1.3.6.1.4.1.34774.4.1.21.4.1.9
		-- 1.3.6.1.4.1.34774.4.1.21.4.1.9
		hwPerfLunReadIORate OBJECT-TYPE
			SYNTAX Unsigned32
			MAX-ACCESS read-only
			STATUS current
			DESCRIPTION
				"Description."
			::= { hwPerfLunEntry 9 }
		
--  1.3.6.1.4.1.34774.4.1.21.4.1.10
		-- 1.3.6.1.4.1.34774.4.1.21.4.1.10
		hwPerfLunWriteIORate OBJECT-TYPE
			SYNTAX Unsigned32
			MAX-ACCESS read-only
			STATUS current
			DESCRIPTION
				"Description."
			::= { hwPerfLunEntry 10 }
		
--  1.3.6.1.4.1.34774.4.1.21.4.1.11
		-- 1.3.6.1.4.1.34774.4.1.21.4.1.11
		hwPerfLunMaxTraffic OBJECT-TYPE
			SYNTAX Unsigned32
			MAX-ACCESS read-only
			STATUS current
			DESCRIPTION
				"Description."
			::= { hwPerfLunEntry 11 }
		
--  1.3.6.1.4.1.34774.4.1.21.4.1.12
		-- 1.3.6.1.4.1.34774.4.1.21.4.1.12
		hwPerfLunMaxIOPS OBJECT-TYPE
			SYNTAX Unsigned32
			MAX-ACCESS read-only
			STATUS current
			DESCRIPTION
				"Description."
			::= { hwPerfLunEntry 12 }
		
--  1.3.6.1.4.1.34774.4.1.21.4.1.13
		-- 1.3.6.1.4.1.34774.4.1.21.4.1.13
		hwPerfLunAverageIOResponseTime OBJECT-TYPE
			SYNTAX Unsigned32
			MAX-ACCESS read-only
			STATUS current
			DESCRIPTION
				"Description."
			::= { hwPerfLunEntry 13 }
		
--  1.3.6.1.4.1.34774.4.1.21.4.1.14
		-- 1.3.6.1.4.1.34774.4.1.21.4.1.14
		hwPerfLunMaxIOResponseTime OBJECT-TYPE
			SYNTAX Unsigned32
			MAX-ACCESS read-only
			STATUS current
			DESCRIPTION
				"Description."
			::= { hwPerfLunEntry 14 }
		
--  1.3.6.1.4.1.34774.4.1.21.4.1.17
		-- 1.3.6.1.4.1.34774.4.1.21.4.1.15
		hwPerfLunAverageReadIOLatency OBJECT-TYPE
			SYNTAX Unsigned32
			MAX-ACCESS read-only
			STATUS current
			DESCRIPTION
				"Description."
			::= { hwPerfLunEntry 15 }
		
--  1.3.6.1.4.1.34774.4.1.21.4.1.18
		-- 1.3.6.1.4.1.34774.4.1.21.4.1.16
		hwPerfLunAverageWriteIOLatency OBJECT-TYPE
			SYNTAX Unsigned32
			MAX-ACCESS read-only
			STATUS current
			DESCRIPTION
				"Description."
			::= { hwPerfLunEntry 16 }
		
--  1.3.6.1.4.1.34774.4.1.21.5
		-- 1.3.6.1.4.1.34774.4.1.21.5
		hwPerfPortTable OBJECT-TYPE
			SYNTAX SEQUENCE OF HwPerfPortEntry
			MAX-ACCESS not-accessible
			STATUS current
			DESCRIPTION
				"Description."
			::= { hwPerformance 5 }
		
--  1.3.6.1.4.1.34774.4.1.21.5.1
		-- 1.3.6.1.4.1.34774.4.1.21.5.1
		hwPerfPortEntry OBJECT-TYPE
			SYNTAX HwPerfPortEntry
			MAX-ACCESS not-accessible
			STATUS current
			DESCRIPTION
				"Description."
			INDEX { hwPerfPortIfIndex }
			::= { hwPerfPortTable 1 }
		
		HwPerfPortEntry ::=
			SEQUENCE { 
				hwPerfPortIfIndex
					Unsigned32,
				hwPerfPortDelay
					Unsigned32,
				hwPerfPortTotalIOPS
					Unsigned32,
				hwPerfPortReadIOPS
					Unsigned32,
				hwPerfPortWriteIOPS
					Unsigned32,
				hwPerfPortTotalTraffic
					Unsigned32,
				hwPerfPortReadTraffic
					Unsigned32,
				hwPerfPortWriteTraffic
					Unsigned32,
				hwPerfPortMaxTraffic
					Unsigned32,
				hwPerfPortMaxIOPS
					Unsigned32,
				hwPerfPortLocation
					OCTET STRING,
				hwPerfPortAverageIOResponseTime
					Unsigned32,
				hwPerfPortMaxIOResponseTime
					Unsigned32,
				hwPerfPortAverageReadIOLatency
					Unsigned32,
				hwPerfPortAverageWriteIOLatency
					Unsigned32
			 }

--  1.3.6.1.4.1.34774.4.1.21.5.1.1
		-- 1.3.6.1.4.1.34774.4.1.21.5.1.1
		hwPerfPortIfIndex OBJECT-TYPE
			SYNTAX Unsigned32
			MAX-ACCESS read-only
			STATUS current
			DESCRIPTION
				"Description."
			::= { hwPerfPortEntry 1 }
		
--  1.3.6.1.4.1.34774.4.1.21.5.1.2
		-- 1.3.6.1.4.1.34774.4.1.21.5.1.2
		hwPerfPortDelay OBJECT-TYPE
			SYNTAX Unsigned32
			MAX-ACCESS read-only
			STATUS current
			DESCRIPTION
				"Description."
			::= { hwPerfPortEntry 2 }
		
--  1.3.6.1.4.1.34774.4.1.21.5.1.3
		-- 1.3.6.1.4.1.34774.4.1.21.5.1.3
		hwPerfPortTotalIOPS OBJECT-TYPE
			SYNTAX Unsigned32
			MAX-ACCESS read-only
			STATUS current
			DESCRIPTION
				" "
			::= { hwPerfPortEntry 3 }
		
--  1.3.6.1.4.1.34774.4.1.21.5.1.4
		-- 1.3.6.1.4.1.34774.4.1.21.5.1.4
		hwPerfPortReadIOPS OBJECT-TYPE
			SYNTAX Unsigned32
			MAX-ACCESS read-only
			STATUS current
			DESCRIPTION
				" "
			::= { hwPerfPortEntry 4 }
		
--  1.3.6.1.4.1.34774.4.1.21.5.1.5
		-- 1.3.6.1.4.1.34774.4.1.21.5.1.5
		hwPerfPortWriteIOPS OBJECT-TYPE
			SYNTAX Unsigned32
			MAX-ACCESS read-only
			STATUS current
			DESCRIPTION
				" "
			::= { hwPerfPortEntry 5 }
		
--  1.3.6.1.4.1.34774.4.1.21.5.1.6
		-- 1.3.6.1.4.1.34774.4.1.21.5.1.6
		hwPerfPortTotalTraffic OBJECT-TYPE
			SYNTAX Unsigned32
			MAX-ACCESS read-only
			STATUS current
			DESCRIPTION
				"Description."
			::= { hwPerfPortEntry 6 }
		
--  1.3.6.1.4.1.34774.4.1.21.5.1.7
		-- 1.3.6.1.4.1.34774.4.1.21.5.1.7
		hwPerfPortReadTraffic OBJECT-TYPE
			SYNTAX Unsigned32
			MAX-ACCESS read-only
			STATUS current
			DESCRIPTION
				"Description."
			::= { hwPerfPortEntry 7 }
		
--  1.3.6.1.4.1.34774.4.1.21.5.1.8
		-- 1.3.6.1.4.1.34774.4.1.21.5.1.8
		hwPerfPortWriteTraffic OBJECT-TYPE
			SYNTAX Unsigned32
			MAX-ACCESS read-only
			STATUS current
			DESCRIPTION
				"Description."
			::= { hwPerfPortEntry 8 }
		
--  1.3.6.1.4.1.34774.4.1.21.5.1.9
		-- 1.3.6.1.4.1.34774.4.1.21.5.1.9
		hwPerfPortMaxTraffic OBJECT-TYPE
			SYNTAX Unsigned32
			MAX-ACCESS read-only
			STATUS current
			DESCRIPTION
				"Description."
			::= { hwPerfPortEntry 9 }
		
--  1.3.6.1.4.1.34774.4.1.21.5.1.10
		-- 1.3.6.1.4.1.34774.4.1.21.5.1.10
		hwPerfPortMaxIOPS OBJECT-TYPE
			SYNTAX Unsigned32
			MAX-ACCESS read-only
			STATUS current
			DESCRIPTION
				"Description."
			::= { hwPerfPortEntry 10 }
		
--  1.3.6.1.4.1.34774.4.1.21.5.1.11
		-- 1.3.6.1.4.1.34774.4.1.21.5.1.11
		hwPerfPortLocation OBJECT-TYPE
			SYNTAX OCTET STRING
			MAX-ACCESS read-only
			STATUS current
			DESCRIPTION
				"Description."
			::= { hwPerfPortEntry 11 }
		
--  1.3.6.1.4.1.34774.4.1.21.5.1.12
		-- 1.3.6.1.4.1.34774.4.1.21.5.1.12
		hwPerfPortAverageIOResponseTime OBJECT-TYPE
			SYNTAX Unsigned32
			MAX-ACCESS read-only
			STATUS current
			DESCRIPTION
				"Description."
			::= { hwPerfPortEntry 12 }
		
--  1.3.6.1.4.1.34774.4.1.21.5.1.13
		-- 1.3.6.1.4.1.34774.4.1.21.5.1.13
		hwPerfPortMaxIOResponseTime OBJECT-TYPE
			SYNTAX Unsigned32
			MAX-ACCESS read-only
			STATUS current
			DESCRIPTION
				"Description."
			::= { hwPerfPortEntry 13 }
		
--  1.3.6.1.4.1.34774.4.1.21.5.1.16
		-- 1.3.6.1.4.1.34774.4.1.21.5.1.14
		hwPerfPortAverageReadIOLatency OBJECT-TYPE
			SYNTAX Unsigned32
			MAX-ACCESS read-only
			STATUS current
			DESCRIPTION
				"Description."
			::= { hwPerfPortEntry 14 }
		
--  1.3.6.1.4.1.34774.4.1.21.5.1.17
		-- 1.3.6.1.4.1.34774.4.1.21.5.1.15
		hwPerfPortAverageWriteIOLatency OBJECT-TYPE
			SYNTAX Unsigned32
			MAX-ACCESS read-only
			STATUS current
			DESCRIPTION
				"Description."
			::= { hwPerfPortEntry 15 }
		
--  1.3.6.1.4.1.34774.4.1.21.7
		-- 1.3.6.1.4.1.34774.4.1.21.7
		hwPerfCacheTable OBJECT-TYPE
			SYNTAX SEQUENCE OF HwPerfCacheEntry
			MAX-ACCESS not-accessible
			STATUS current
			DESCRIPTION
				"Description."
			::= { hwPerformance 7 }
		
--  1.3.6.1.4.1.34774.4.1.21.7.1
		-- 1.3.6.1.4.1.34774.4.1.21.7.1
		hwPerfCacheEntry OBJECT-TYPE
			SYNTAX HwPerfCacheEntry
			MAX-ACCESS not-accessible
			STATUS current
			DESCRIPTION
				"Description."
			INDEX { hwPerfCacheID }
			::= { hwPerfCacheTable 1 }
		
		HwPerfCacheEntry ::=
			SEQUENCE { 
				hwPerfCacheID
					Unsigned32,
				hwPerfCacheReadUtilization
					Integer32,
				hwPerfCacheWriteUtilization
					Integer32,
				hwPerfCacheMirrorWriteUtilization
					Integer32,
				hwPerfCacheHitRatio
					Integer32
			 }

--  1.3.6.1.4.1.34774.4.1.21.7.1.1
		-- 1.3.6.1.4.1.34774.4.1.21.7.1.1
		hwPerfCacheID OBJECT-TYPE
			SYNTAX Unsigned32
			MAX-ACCESS read-write
			STATUS current
			DESCRIPTION
				"Description."
			::= { hwPerfCacheEntry 1 }
		
--  1.3.6.1.4.1.34774.4.1.21.7.1.2
		-- 1.3.6.1.4.1.34774.4.1.21.7.1.2
		hwPerfCacheReadUtilization OBJECT-TYPE
			SYNTAX Integer32
			MAX-ACCESS read-only
			STATUS current
			DESCRIPTION
				"Description."
			::= { hwPerfCacheEntry 2 }
		
--  1.3.6.1.4.1.34774.4.1.21.7.1.3
		-- 1.3.6.1.4.1.34774.4.1.21.7.1.3
		hwPerfCacheWriteUtilization OBJECT-TYPE
			SYNTAX Integer32
			MAX-ACCESS read-only
			STATUS current
			DESCRIPTION
				"Description."
			::= { hwPerfCacheEntry 3 }
		
--  1.3.6.1.4.1.34774.4.1.21.7.1.4
		-- 1.3.6.1.4.1.34774.4.1.21.7.1.4
		hwPerfCacheMirrorWriteUtilization OBJECT-TYPE
			SYNTAX Integer32
			MAX-ACCESS read-only
			STATUS current
			DESCRIPTION
				"Description."
			::= { hwPerfCacheEntry 4 }
		
--  1.3.6.1.4.1.34774.4.1.21.7.1.5
		-- 1.3.6.1.4.1.34774.4.1.21.7.1.5
		hwPerfCacheHitRatio OBJECT-TYPE
			SYNTAX Integer32
			MAX-ACCESS read-only
			STATUS current
			DESCRIPTION
				"Description."
			::= { hwPerfCacheEntry 5 }

		hwPerfControllerNFSV3Table OBJECT-TYPE
			SYNTAX SEQUENCE OF HwPerfControllerNFSV3Entry
			MAX-ACCESS not-accessible
			STATUS current
			DESCRIPTION
				" "
			::= { hwPerformance 10 }


		hwPerfControllerNFSV3Entry OBJECT-TYPE
			SYNTAX HwPerfControllerNFSV3Entry
			MAX-ACCESS not-accessible
			STATUS current
			DESCRIPTION
				"Description."
			INDEX { hwPerfControllerNFSV3ID }
			::= { hwPerfControllerNFSV3Table 1 }


		HwPerfControllerNFSV3Entry ::=
			SEQUENCE {
				hwPerfControllerNFSV3ID
					OCTET STRING,
				hwPerfControllerNFSV3OPS
					Counter64,
				hwPerfControllerNFSV3Bps
					Counter64
			 }

		hwPerfControllerNFSV3ID OBJECT-TYPE
			SYNTAX OCTET STRING
			MAX-ACCESS read-only
			STATUS current
			DESCRIPTION
				" "
			::= { hwPerfControllerNFSV3Entry 1 }


		hwPerfControllerNFSV3OPS OBJECT-TYPE
			SYNTAX Counter64
			MAX-ACCESS read-only
			STATUS current
			DESCRIPTION
				" "
			::= { hwPerfControllerNFSV3Entry 2 }


		hwPerfControllerNFSV3Bps OBJECT-TYPE
			SYNTAX Counter64
			MAX-ACCESS read-only
			STATUS current
			DESCRIPTION
				" "
			::= { hwPerfControllerNFSV3Entry 3 }


		hwPerfControllerNFSV4Table OBJECT-TYPE
			SYNTAX SEQUENCE OF HwPerfControllerNFSV4Entry
			MAX-ACCESS not-accessible
			STATUS current
			DESCRIPTION
				" "
			::= { hwPerformance 11 }


		hwPerfControllerNFSV4Entry OBJECT-TYPE
			SYNTAX HwPerfControllerNFSV4Entry
			MAX-ACCESS not-accessible
			STATUS current
			DESCRIPTION
				"Description."
			INDEX { hwPerfControllerNFSV4ID }
			::= { hwPerfControllerNFSV4Table 1 }


		HwPerfControllerNFSV4Entry ::=
			SEQUENCE {
				hwPerfControllerNFSV4ID
					OCTET STRING,
				hwPerfControllerNFSV4OPS
					Counter64,
				hwPerfControllerNFSV4Bps
					Counter64
			 }

		hwPerfControllerNFSV4ID OBJECT-TYPE
			SYNTAX OCTET STRING
			MAX-ACCESS read-only
			STATUS current
			DESCRIPTION
				" "
			::= { hwPerfControllerNFSV4Entry 1 }


		hwPerfControllerNFSV4OPS OBJECT-TYPE
			SYNTAX Counter64
			MAX-ACCESS read-only
			STATUS current
			DESCRIPTION
				" "
			::= { hwPerfControllerNFSV4Entry 2 }


		hwPerfControllerNFSV4Bps OBJECT-TYPE
			SYNTAX Counter64
			MAX-ACCESS read-only
			STATUS current
			DESCRIPTION
				" "
			::= { hwPerfControllerNFSV4Entry 3 }


		hwPerfControllerSMBV1Table OBJECT-TYPE
			SYNTAX SEQUENCE OF HwPerfControllerSMBV1Entry
			MAX-ACCESS not-accessible
			STATUS current
			DESCRIPTION
				" "
			::= { hwPerformance 12 }


		hwPerfControllerSMBV1Entry OBJECT-TYPE
			SYNTAX HwPerfControllerSMBV1Entry
			MAX-ACCESS not-accessible
			STATUS current
			DESCRIPTION
				"Description."
			INDEX { hwPerfControllerSMBV1ID }
			::= { hwPerfControllerSMBV1Table 1 }


		HwPerfControllerSMBV1Entry ::=
			SEQUENCE {
				hwPerfControllerSMBV1ID
					OCTET STRING,
				hwPerfControllerSMBV1OPS
					Counter64,
				hwPerfControllerSMBV1Bps
					Counter64
			 }

		hwPerfControllerSMBV1ID OBJECT-TYPE
			SYNTAX OCTET STRING
			MAX-ACCESS read-only
			STATUS current
			DESCRIPTION
				" "
			::= { hwPerfControllerSMBV1Entry 1 }


		hwPerfControllerSMBV1OPS OBJECT-TYPE
			SYNTAX Counter64
			MAX-ACCESS read-only
			STATUS current
			DESCRIPTION
				" "
			::= { hwPerfControllerSMBV1Entry 2 }


		hwPerfControllerSMBV1Bps OBJECT-TYPE
			SYNTAX Counter64
			MAX-ACCESS read-only
			STATUS current
			DESCRIPTION
				" "
			::= { hwPerfControllerSMBV1Entry 3 }


		hwPerfControllerSMBV2Table OBJECT-TYPE
			SYNTAX SEQUENCE OF HwPerfControllerSMBV2Entry
			MAX-ACCESS not-accessible
			STATUS current
			DESCRIPTION
				" "
			::= { hwPerformance 13 }


		hwPerfControllerSMBV2Entry OBJECT-TYPE
			SYNTAX HwPerfControllerSMBV2Entry
			MAX-ACCESS not-accessible
			STATUS current
			DESCRIPTION
				"Description."
			INDEX { hwPerfControllerSMBV2ID }
			::= { hwPerfControllerSMBV2Table 1 }


		HwPerfControllerSMBV2Entry ::=
			SEQUENCE {
				hwPerfControllerSMBV2ID
					OCTET STRING,
				hwPerfControllerSMBV2OPS
					Counter64,
				hwPerfControllerSMBV2Bps
					Counter64
			 }

		hwPerfControllerSMBV2ID OBJECT-TYPE
			SYNTAX OCTET STRING
			MAX-ACCESS read-only
			STATUS current
			DESCRIPTION
				" "
			::= { hwPerfControllerSMBV2Entry 1 }


		hwPerfControllerSMBV2OPS OBJECT-TYPE
			SYNTAX Counter64
			MAX-ACCESS read-only
			STATUS current
			DESCRIPTION
				" "
			::= { hwPerfControllerSMBV2Entry 2 }


		hwPerfControllerSMBV2Bps OBJECT-TYPE
			SYNTAX Counter64
			MAX-ACCESS read-only
			STATUS current
			DESCRIPTION
				" "
			::= { hwPerfControllerSMBV2Entry 3 }


		hwPerfFileSystemTable OBJECT-TYPE
			SYNTAX SEQUENCE OF HwPerfFileSystemEntry
			MAX-ACCESS not-accessible
			STATUS current
			DESCRIPTION
				" "
			::= { hwPerformance 14 }


		hwPerfFileSystemEntry OBJECT-TYPE
			SYNTAX HwPerfFileSystemEntry
			MAX-ACCESS not-accessible
			STATUS current
			DESCRIPTION
				"Description."
			INDEX { hwPerfFileSystemID }
			::= { hwPerfFileSystemTable 1 }


		HwPerfFileSystemEntry ::=
			SEQUENCE {
				hwPerfFileSystemID
					OCTET STRING,
				hwPerfFileSystemOPS
					Counter64,
				hwPerfFileSystemServiceTime
					Counter64,
				hwPerfFileSystemReadOPS
					Counter64,
				hwPerfFileSystemReadBandwidth
					Counter64,
				hwPerfFileSystemAvRdOPSRspTime
					Counter64,
				hwPerfFileSystemAvWrOPSRspTime
					Counter64,
				hwPerfFileSystemWriteOPS
					Counter64,
				hwPerfFileSystemWriteBandwidth
					Counter64
			 }

		hwPerfFileSystemID OBJECT-TYPE
			SYNTAX OCTET STRING
			MAX-ACCESS read-only
			STATUS current
			DESCRIPTION
				" "
			::= { hwPerfFileSystemEntry 1 }


		hwPerfFileSystemOPS OBJECT-TYPE
			SYNTAX Counter64
			MAX-ACCESS read-only
			STATUS current
			DESCRIPTION
				" "
			::= { hwPerfFileSystemEntry 2 }


		hwPerfFileSystemServiceTime OBJECT-TYPE
			SYNTAX Counter64
			MAX-ACCESS read-only
			STATUS current
			DESCRIPTION
				" "
			::= { hwPerfFileSystemEntry 3 }


		hwPerfFileSystemReadOPS OBJECT-TYPE
			SYNTAX Counter64
			MAX-ACCESS read-only
			STATUS current
			DESCRIPTION
				" "
			::= { hwPerfFileSystemEntry 4 }


		hwPerfFileSystemReadBandwidth OBJECT-TYPE
			SYNTAX Counter64
			MAX-ACCESS read-only
			STATUS current
			DESCRIPTION
				" "
			::= { hwPerfFileSystemEntry 5 }


		hwPerfFileSystemAvRdOPSRspTime OBJECT-TYPE
			SYNTAX Counter64
			MAX-ACCESS read-only
			STATUS current
			DESCRIPTION
				" "
			::= { hwPerfFileSystemEntry 6 }


		hwPerfFileSystemAvWrOPSRspTime OBJECT-TYPE
			SYNTAX Counter64
			MAX-ACCESS read-only
			STATUS current
			DESCRIPTION
				" "
			::= { hwPerfFileSystemEntry 7 }


		hwPerfFileSystemWriteOPS OBJECT-TYPE
			SYNTAX Counter64
			MAX-ACCESS read-only
			STATUS current
			DESCRIPTION
				" "
			::= { hwPerfFileSystemEntry 8 }


		hwPerfFileSystemWriteBandwidth OBJECT-TYPE
			SYNTAX Counter64
			MAX-ACCESS read-only
			STATUS current
			DESCRIPTION
				" "
			::= { hwPerfFileSystemEntry 9 }

		
--  1.6
		-- 1.6
		isoConformance OBJECT IDENTIFIER ::= { iso 6 }
		
--  1.6.1
		-- 1.6.1
		isoGroups OBJECT IDENTIFIER ::= { isoConformance 1 }
		
--  1.6.1.1
		-- 1.6.1.1
		currentObjectGroup OBJECT-GROUP
			OBJECTS { hwPerfNodeCPUUsage, hwPerfNodeMemoryUsage, hwPerfLunTotalIOPS, hwPerfLunHitRate, hwPerfLunReadIOPS, 
				hwPerfLunWriteIOPS, hwPerfLunTotalTraffic, hwPerfLunReadTraffic, hwPerfLunWriteTraffic, hwPerfPortDelay, 
				hwPerfPortTotalIOPS, hwPerfPortReadIOPS, hwPerfPortWriteIOPS, hwPerfPortTotalTraffic, hwPerfPortReadTraffic, 
				hwPerfPortWriteTraffic, hwPerfNodeDelay, hwPerfNodeTotalIOPS, hwPerfNodeReadIOPS, hwPerfNodeWriteIOPS, 
				hwPerfNodeTotalTraffic, hwPerfNodeReadTraffic, hwPerfNodeWriteTraffic, hwPerfLunID, hwPerfPortIfIndex, 
				hwPerfLunWriteIORate, hwPerfLunReadIORate, hwPerfCacheID, hwPerfCacheReadUtilization, hwPerfCacheWriteUtilization, 
				hwPerfCacheMirrorWriteUtilization, hwPerfCacheHitRatio, hwPerfLunMaxTraffic, hwPerfLunMaxIOPS, hwPerfPortMaxTraffic, 
				hwPerfPortLocation, hwPerfNodeAverageIOResponseTime, hwPerfNodeMaxIOResponseTime, hwPerfNodeAverageReadIOLatency, hwPerfNodeAverageWriteIOLatency, 
				hwPerfLunAverageIOResponseTime, hwPerfLunMaxIOResponseTime, hwPerfLunAverageReadIOLatency, hwPerfLunAverageWriteIOLatency, hwPerfPortAverageIOResponseTime, 
				hwPerfPortMaxIOResponseTime, hwPerfPortAverageReadIOLatency, hwPerfPortAverageWriteIOLatency, hwPerfPortMaxIOPS, hwPerformanceSwitch, 
				hwPerfControllerNFSV3ID, hwPerfControllerNFSV4ID, hwPerfControllerSMBV1ID, hwPerfControllerSMBV2ID,
				hwPerfNodeFileBandwidth, hwPerfNodeFileOPS, hwPerfControllerNFSV3Bps, hwPerfControllerNFSV3OPS,
				hwPerfControllerNFSV4OPS, hwPerfControllerNFSV4Bps, hwPerfControllerSMBV1OPS, hwPerfControllerSMBV2OPS, hwPerfControllerSMBV2Bps,
				hwPerfFileSystemOPS, hwPerfFileSystemServiceTime, hwPerfFileSystemReadOPS, hwPerfFileSystemReadBandwidth, hwPerfFileSystemWriteOPS,
				hwPerfFileSystemWriteBandwidth,
				hwPerfNodeIfIndex }
			STATUS current
			DESCRIPTION 
				"Enter the description of the created OBJECT-GROUP."
			::= { isoGroups 1 }
		
--  1.6.2
		-- 1.6.2
		isoCompliances OBJECT IDENTIFIER ::= { isoConformance 2 }
		
--   this module
-- 1.6.2.1
-- this module
		-- 1.6.2.1
		basicCompliance MODULE-COMPLIANCE
			STATUS current
			DESCRIPTION 
				"Enter the description of the created MODULE-COMPLIANCE."
			MODULE -- this module
				MANDATORY-GROUPS { currentObjectGroup }
			::= { isoCompliances 1 }
		
	
	END

--
-- ISM-PERFORMANCE-MIB.mib
--
